# -*- coding: utf-8 -*-
# MenuText: Preparar red TCOM completa (Legacy)
# Icon: Conectar/Preparar_Red_TCOM_Completa.svg
# Toolbar: Conectar Legacy
# Transaction: self

"""Orquestador TCOM basado en los motores generales ElectricCR.

No carga macros geometricas mediante exec(). Mantiene la presentacion roja de
los tomacorrientes de computo como ultimo paso. Compatible con FreeCAD 1.1.3.
Revision: 2026-08-08.
"""

from pathlib import Path
import sys
import unicodedata
import FreeCAD as App


def _normalized(value):
    raw = unicodedata.normalize("NFD", str(value or ""))
    return "".join(char for char in raw if unicodedata.category(char) != "Mn").lower()


def _paint_computer_outlets(doc):
    outlets = []
    for obj in list(doc.Objects):
        if hasattr(obj, "Group"):
            continue
        if str(getattr(obj, "TypeId", "")) != "App::Link" and not hasattr(obj, "LinkedObject"):
            continue
        circuit = _normalized(getattr(obj, "CircuitoID", ""))
        system = " ".join(_normalized(getattr(obj, prop, "")) for prop in ("Sistema", "UsoElectrico", "ClaseCSV"))
        imported = _normalized(getattr(obj, "Name", "")).startswith("toma_computo_dxf_")
        if circuit.startswith("tcom-") or "computo" in system or imported:
            outlets.append(obj)
    painted = 0
    for obj in outlets:
        view = getattr(obj, "ViewObject", None)
        if view is None:
            continue
        changed = False
        for prop in ("ShapeColor", "LineColor", "PointColor"):
            if hasattr(view, prop):
                try:
                    setattr(view, prop, (1.0, 0.05, 0.05))
                    changed = True
                except Exception:
                    pass
        painted += int(changed)
    return {"encontrados": len(outlets), "pintados": painted}


def main(doc_override=None):
    root = Path(__file__).resolve().parent.parent
    if str(root) not in sys.path:
        sys.path.insert(0, str(root))
    from ElectricCR.electriccr.connections import backbone, feeders

    doc = doc_override or App.ActiveDocument
    if doc is None:
        return None
    feeder_result = feeders.connect_circuit_feeders(
        doc,
        panel_code="TCOM",
        circuit_prefix="TCOM",
        cfg={"route_z": 3400.0, "lane_spacing": 50.0, "approach_clearance": 300.0, "bend_radius": 100.0, "port_stub": 80.0},
    )
    if feeder_result.get("errors"):
        return None
    branch_result = backbone.connect_backbone(
        doc,
        circuit_prefix="TCOM",
        cfg={"route_z": 3400.0, "bend_radius": 100.0, "port_stub": 80.0, "diameter": 22.2},
    )
    if branch_result.get("errors"):
        return None
    color_result = _paint_computer_outlets(doc)
    doc.recompute()
    return {"alimentadores": feeder_result, "ramales": branch_result, "color": color_result}


if __name__ == "__main__":
    main()

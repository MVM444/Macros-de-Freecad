# -*- coding: utf-8 -*-
# ======================================================================
# MACRO: Fix_Link_Transform_FreeCAD
# Fecha: 2026-03-23
# Objetivo:
#   Diagnosticar y normalizar App::Link cuando Transform (menu contextual)
#   aparece deshabilitado en FreeCAD.
#
# Notas:
# - No usa comandos GUI (Std_TransformManip / Std_Placement).
# - Usa Placement como metodo principal para mover/rotar links.
# - Compatible con FreeCAD 0.21+ / 1.0+ (enfoque defensivo).
# ======================================================================

import FreeCAD as App

try:
    import FreeCADGui as Gui
except Exception:
    Gui = None

REVIEW_GROUP_LABEL = "REVISAR_LINKS"
MARK_PROBLEMATIC = True


def _log(msg):
    App.Console.PrintMessage("[LINK_FIX][INFO] {}\n".format(msg))


def _warn(msg):
    App.Console.PrintWarning("[LINK_FIX][WARN] {}\n".format(msg))


def _err(msg):
    App.Console.PrintError("[LINK_FIX][ERROR] {}\n".format(msg))


def _doc(doc=None):
    d = doc or App.ActiveDocument
    if d is None:
        raise RuntimeError("No active document")
    return d


def _is_link(obj):
    return str(getattr(obj, "TypeId", "")) == "App::Link"


def _is_link_element(obj):
    return "LinkElement" in str(getattr(obj, "TypeId", ""))


def _vec_text(v):
    try:
        return "({:.2f}, {:.2f}, {:.2f})".format(float(v.x), float(v.y), float(v.z))
    except Exception:
        return "(?, ?, ?)"


def _placement_text(obj):
    try:
        pl = getattr(obj, "Placement", None)
        if pl is None:
            return "Placement=None"
        base = _vec_text(pl.Base)
        ang = float(getattr(pl.Rotation, "Angle", 0.0))
        return "Placement.Base={} Rot.Angle={:.4f}".format(base, ang)
    except Exception:
        return "Placement=?"


def _container_chain(obj):
    chain = []
    seen = set()
    stack = list(getattr(obj, "InList", []) or [])
    while stack:
        parent = stack.pop(0)
        pid = getattr(parent, "Name", None) or id(parent)
        if pid in seen:
            continue
        seen.add(pid)
        chain.append(parent)
        for p2 in (getattr(parent, "InList", []) or []):
            stack.append(p2)
    return chain


def _container_info(obj):
    chain = _container_chain(obj)
    labels = []
    restrictive = False
    restrictive_hits = []

    restrictive_hints = (
        "PartDesign::Body",
        "PartDesign::Feature",
        "PartDesign::",
    )

    for parent in chain:
        tid = str(getattr(parent, "TypeId", ""))
        lbl = str(getattr(parent, "Label", getattr(parent, "Name", "?")))
        labels.append("{}<{}>".format(lbl, tid))
        if any(tid.startswith(h) for h in restrictive_hints):
            restrictive = True
            restrictive_hits.append("{}<{}>".format(lbl, tid))

    return {
        "restrictive": restrictive,
        "restrictive_hits": restrictive_hits,
        "chain_text": " > ".join(labels) if labels else "(root)",
    }


def _ensure_review_group(doc):
    grp = doc.getObject(REVIEW_GROUP_LABEL)
    if grp is None:
        grp = doc.addObject("App::DocumentObjectGroup", REVIEW_GROUP_LABEL)
        try:
            grp.Label = REVIEW_GROUP_LABEL
        except Exception:
            pass
    return grp


def scan_links(doc=None):
    """
    Lista todos los App::Link y muestra estado tecnico.
    """
    d = _doc(doc)
    links = [o for o in (d.Objects or []) if _is_link(o)]
    _log("scan_links: links_detected={}".format(len(links)))

    for i, lk in enumerate(links, start=1):
        linked = getattr(lk, "LinkedObject", None)
        linked_name = getattr(linked, "Name", "None") if linked is not None else "None"

        try:
            lt = bool(getattr(lk, "LinkTransform", False))
        except Exception:
            lt = False

        cinfo = _container_info(lk)
        flags = []
        if lt is False:
            flags.append("LinkTransform=False")
        if _is_link_element(lk):
            flags.append("LinkElement")
        if cinfo["restrictive"]:
            flags.append("RestrictiveContainer")

        _log(
            "  {:03d} | {} ({}) | linked={} | {} | flags={} | containers={}".format(
                i,
                getattr(lk, "Label", lk.Name),
                lk.Name,
                linked_name,
                _placement_text(lk),
                ",".join(flags) if flags else "ok",
                cinfo["chain_text"],
            )
        )
    return links


def fix_link(link, mark_group=MARK_PROBLEMATIC):
    """
    Normaliza un App::Link para dejarlo transformable por Placement.

    Reglas aplicadas:
    - Reasigna enlace al LinkedObject actual (setLink o LinkedObject)
    - Activa LinkTransform
    - Desbloquea Placement / LinkPlacement
    - Fuerza Placement limpio
    - Marca problematicos en grupo REVISAR_LINKS (opcional)
    """
    if not _is_link(link):
        raise TypeError("fix_link requires App::Link")

    changed = []
    warnings = []

    linked = getattr(link, "LinkedObject", None)
    if linked is None:
        warnings.append("broken_link_no_linked_object")
    else:
        try:
            if hasattr(link, "setLink"):
                link.setLink(linked)
                changed.append("setLink")
            else:
                link.LinkedObject = linked
                changed.append("set_LinkedObject")
        except Exception as ex:
            warnings.append("setLink_failed:{}".format(ex))

    # Ensure transform support
    try:
        if getattr(link, "LinkTransform", None) is not True:
            link.LinkTransform = True
            changed.append("LinkTransform=True")
    except Exception as ex:
        warnings.append("LinkTransform_failed:{}".format(ex))

    # Unlock editor mode
    for prop in ("Placement", "LinkPlacement"):
        try:
            link.setEditorMode(prop, 0)
            changed.append("setEditorMode:{}".format(prop))
        except Exception:
            pass
        try:
            link.setPropertyStatus(prop, [])
            changed.append("setPropertyStatus:{}".format(prop))
        except Exception:
            pass

    # Force clean placement object
    try:
        pl = getattr(link, "Placement", App.Placement())
        clean = App.Placement(App.Vector(pl.Base.x, pl.Base.y, pl.Base.z), pl.Rotation)
        link.Placement = clean
        changed.append("Placement_clean")
    except Exception as ex:
        warnings.append("Placement_clean_failed:{}".format(ex))

    # Touch LinkPlacement if present
    try:
        if hasattr(link, "LinkPlacement"):
            lp = getattr(link, "LinkPlacement")
            link.LinkPlacement = lp
            changed.append("LinkPlacement_touch")
    except Exception:
        pass

    # Ensure selectable in GUI
    try:
        if hasattr(link, "ViewObject") and link.ViewObject is not None:
            if getattr(link.ViewObject, "Selectable", True) is False:
                link.ViewObject.Selectable = True
                changed.append("ViewObject.Selectable=True")
    except Exception:
        pass

    cinfo = _container_info(link)
    if cinfo["restrictive"]:
        warnings.append("restrictive_container")
    if _is_link_element(link):
        warnings.append("link_element")

    if mark_group and warnings:
        try:
            grp = _ensure_review_group(link.Document)
            if link not in (getattr(grp, "Group", []) or []):
                grp.addObject(link)
                changed.append("marked_REVISAR_LINKS")
        except Exception as ex:
            warnings.append("mark_group_failed:{}".format(ex))

    _log(
        "fix_link: {} ({}) | changed={} | warnings={}".format(
            getattr(link, "Label", link.Name),
            link.Name,
            len(changed),
            ",".join(warnings) if warnings else "none",
        )
    )

    return {
        "object": link,
        "changed": changed,
        "warnings": warnings,
        "container": cinfo,
    }


def move_link(link, x, y, z, relative=True):
    """
    Mueve un link via Placement (sin comandos GUI).
    """
    if not _is_link(link):
        raise TypeError("move_link requires App::Link")

    pl = getattr(link, "Placement", App.Placement())
    dx = float(x)
    dy = float(y)
    dz = float(z)

    if relative:
        new_base = App.Vector(pl.Base.x + dx, pl.Base.y + dy, pl.Base.z + dz)
    else:
        new_base = App.Vector(dx, dy, dz)

    link.Placement = App.Placement(new_base, pl.Rotation)
    _log("move_link: {} -> {}".format(getattr(link, "Name", "?"), _vec_text(new_base)))
    return new_base


def fix_all_links(doc=None, mark_group=MARK_PROBLEMATIC):
    """
    Aplica fix_link a todos los App::Link del documento.
    """
    d = _doc(doc)
    links = [o for o in (d.Objects or []) if _is_link(o)]
    _log("fix_all_links: total_links={}".format(len(links)))

    changed_count = 0
    warn_count = 0
    results = []

    for lk in links:
        try:
            res = fix_link(lk, mark_group=mark_group)
            results.append(res)
            if res["changed"]:
                changed_count += 1
            if res["warnings"]:
                warn_count += 1
        except Exception as ex:
            _warn("fix_all_links failed on {}: {}".format(getattr(lk, "Name", "?"), ex))

    try:
        d.recompute()
    except Exception as ex:
        _warn("recompute warning: {}".format(ex))

    _log("fix_all_links done: changed_links={} | warning_links={}".format(changed_count, warn_count))
    return results


# ----------------------------------------------------------------------
# Uso rapido en consola:
# 1) scan_links()
# 2) fix_all_links()
# 3) move_link(App.ActiveDocument.getObject("LinkName"), 100, 0, 0)
# ----------------------------------------------------------------------

if __name__ == "__main__":
    try:
        scan_links()
        fix_all_links()
    except Exception as _ex:
        _err(str(_ex))

import FreeCAD
import FreeCADGui
import Draft
import re
import os
import sys
_THIS_DIR = os.path.dirname(__file__) if '__file__' in globals() else ''
if _THIS_DIR and _THIS_DIR not in sys.path:
    sys.path.insert(0, _THIS_DIR)
import importlib
import conexiones_grouping as _conexiones_grouping_mod
_conexiones_grouping_mod = importlib.reload(_conexiones_grouping_mod)
ensure_conexiones_group = _conexiones_grouping_mod.ensure_conexiones_group
EPS = 1e-6


def _make_wire(points):
    maker = getattr(Draft, "make_wire", None)
    if maker is None:
        maker = getattr(Draft, "makeWire", None)
    if maker is None:
        raise RuntimeError("No se encontro Draft.make_wire ni Draft.makeWire")

    attempts = [
        lambda: maker(points, closed=False, face=False),
        lambda: maker(points, False, False),
        lambda: maker(points, False),
        lambda: maker(points),
    ]
    last_err = None
    for attempt in attempts:
        try:
            return attempt()
        except Exception as ex:
            last_err = ex
    raise RuntimeError(f"No se pudo crear wire: {last_err}")


def _add_point(seq, p):
    if not seq:
        seq.append(p)
        return
    if seq[-1].distanceToPoint(p) > EPS:
        seq.append(p)


def ordenar_por_etiqueta(objetos):
    def sort_key(obj):
        parts = re.split(r"(\d+)", obj.Label)
        return [int(part) if part.isdigit() else part for part in parts]

    return sorted(objetos, key=sort_key)


def conectar_tomacorrientes_con_polilinea():
    doc = FreeCAD.ActiveDocument
    if doc is None:
        FreeCAD.Console.PrintError("No hay documento activo.\n")
        return

    selected_objects = FreeCADGui.Selection.getSelection()
    if not selected_objects:
        FreeCAD.Console.PrintError("No se ha seleccionado ningun objeto.\n")
        return

    if selected_objects[0].TypeId == "App::DocumentObjectGroup":
        grupo = selected_objects[0]
    else:
        grupo = None
        for obj in doc.Objects:
            if obj.TypeId == "App::DocumentObjectGroup" and selected_objects[0] in obj.Group:
                grupo = obj
                break
        if grupo is None:
            FreeCAD.Console.PrintError("El objeto seleccionado no pertenece a ningun grupo.\n")
            return

    FreeCAD.Console.PrintMessage(f"Grupo seleccionado: {grupo.Name}\n")

    objetos_numerados = ordenar_por_etiqueta([obj for obj in grupo.Group if re.search(r"\d+", obj.Label)])

    puntos = []
    for obj in objetos_numerados:
        if hasattr(obj, "Placement"):
            puntos.append(obj.Placement.Base)
        else:
            FreeCAD.Console.PrintWarning(f"El objeto {obj.Label} no tiene Placement.\n")

    if len(puntos) < 2:
        FreeCAD.Console.PrintError("No hay suficientes tomacorrientes en el grupo para crear una ruta.\n")
        return

    # Construir ruta ortogonal continua
    ruta = []
    _add_point(ruta, puntos[0])

    for i in range(len(puntos) - 1):
        p1 = puntos[i]
        p2 = puntos[i + 1]
        if p1.distanceToPoint(p2) <= EPS:
            FreeCAD.Console.PrintWarning(f"Se omitio segmento entre puntos iguales: {p1}\n")
            continue

        mid_point = FreeCAD.Vector(p2.x, p1.y, p1.z)
        _add_point(ruta, mid_point)
        _add_point(ruta, p2)

    if len(ruta) < 2:
        FreeCAD.Console.PrintError("No se pudo construir una ruta valida.\n")
        return

    wire = _make_wire(ruta)
    wire.Label = f"Conexion_Tomas_{grupo.Label}"
    conexiones_grupo = ensure_conexiones_group(doc, parent_group=grupo, objects=objetos_numerados)
    try:
        conexiones_grupo.addObject(wire)
    except Exception:
        pass

    if hasattr(wire, "FilletRadius"):
        try:
            wire.FilletRadius = 10.0
        except Exception as ex:
            FreeCAD.Console.PrintWarning(f"No se pudo aplicar FilletRadius: {ex}\n")

    doc.recompute()


# Ejecuta la funcion para conectar tomacorrientes en el grupo seleccionado
conectar_tomacorrientes_con_polilinea()

# -*- coding: utf-8 -*-
# MenuText: Reemplazar tomacorrientes (registro)
# Icon: InsertarTomacorriente.svg

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

"""
Reemplaza tomacorrientes por otra clave del registro ElectricCR.

Soporta:
- Actualizacion en sitio (si el objeto ya es FeaturePython con KeyRegistro).
- Reemplazo fisico (si el objeto no soporta KeyRegistro), preservando placement,
  label y pertenencia a grupos.
"""

import json
import sys
import importlib
import importlib.util
import importlib.machinery
from pathlib import Path

import FreeCAD as App
import FreeCADGui as Gui

try:
    from PySide2 import QtWidgets
except Exception:
    from PySide import QtGui as QtWidgets


TAG = "[REEMP-TOMA]"
EPS_MM = 0.01


def _log(msg):
    App.Console.PrintMessage(f"{TAG}[INFO] {msg}\n")


def _warn(msg):
    App.Console.PrintWarning(f"{TAG}[WARN] {msg}\n")


def _err(msg):
    App.Console.PrintError(f"{TAG}[ERROR] {msg}\n")


def _this_dir():
    try:
        return Path(__file__).resolve().parent
    except Exception:
        return None


def _candidate_pkg_roots():
    seen = set()
    base = _this_dir()
    if base is not None:
        macros_dir = base.parent
        for candidate in (macros_dir / "ElectricCR", macros_dir.parent / "ElectricCR"):
            if candidate and candidate not in seen:
                seen.add(candidate)
                yield candidate
    try:
        user_mod = Path(App.getUserAppDataDir()) / "Mod" / "ElectricCR"
        if user_mod not in seen:
            seen.add(user_mod)
            yield user_mod
    except Exception:
        pass


def _ensure_paths():
    base = _this_dir()
    if base is not None:
        con_dir = base.parent / "Conectar"
        if con_dir.is_dir() and str(con_dir) not in sys.path:
            sys.path.insert(0, str(con_dir))
    for root in _candidate_pkg_roots():
        try:
            if root.is_dir() and str(root) not in sys.path:
                sys.path.insert(0, str(root))
        except Exception:
            continue


def _fallback_loader():
    for root in _candidate_pkg_roots():
        try:
            cand = root / "electriccr" / "features" / "objeto_toma_uno.py"
        except Exception:
            continue
        if cand.is_file():
            loader = importlib.machinery.SourceFileLoader("objeto_toma_uno_boot", str(cand))
            spec = importlib.util.spec_from_loader(loader.name, loader)
            if spec is None:
                continue
            module = importlib.util.module_from_spec(spec)
            loader.exec_module(module)
            return module
    return None


def _load_toma_module():
    _ensure_paths()
    try:
        module = importlib.import_module("electriccr.features.objeto_toma_uno")
        importlib.reload(module)
        return module
    except Exception:
        module = _fallback_loader()
        if module is None:
            _err("No se pudo cargar electriccr.features.objeto_toma_uno")
            raise
        return module


def _load_classifier():
    _ensure_paths()
    try:
        mod = importlib.import_module("component_classifier")
        mod = importlib.reload(mod)
        return mod
    except Exception:
        return None


def _registry_path():
    base = _this_dir()
    if base is None:
        return None
    candidate = base.parent / "Resources" / "registry" / "registry_electric.json"
    return candidate if candidate.is_file() else None


def _load_toma_keys():
    path = _registry_path()
    if path is None:
        return []
    try:
        data = json.loads(path.read_text(encoding="utf-8"))
    except Exception:
        try:
            data = json.loads(path.read_text(encoding="latin-1"))
        except Exception as ex:
            _warn(f"No se pudo leer registry_electric.json: {ex}")
            return []
    types = data.get("types", {}) if isinstance(data, dict) else {}
    keys = []
    for k in types.keys():
        s = str(k or "")
        if s.lower().startswith("tomacorriente"):
            keys.append(s)
    return sorted(keys)


def _is_group(obj):
    if obj is None:
        return False
    try:
        if obj.isDerivedFrom("App::DocumentObjectGroup"):
            return True
    except Exception:
        pass
    return hasattr(obj, "Group")


def _is_conexiones_group(obj):
    label = str(getattr(obj, "Label", "") or "").strip().lower()
    name = str(getattr(obj, "Name", "") or "").strip().lower()
    return label.startswith("conexiones") or name.startswith("conexiones")


def _iter_group_objects(grp):
    if not _is_group(grp):
        return
    for child in (getattr(grp, "Group", []) or []):
        if _is_group(child):
            if _is_conexiones_group(child):
                continue
            for sub in _iter_group_objects(child):
                yield sub
        else:
            yield child


def _find_group_by_label(doc, label):
    target = str(label or "").strip().lower()
    if not target:
        return None
    for obj in getattr(doc, "Objects", []) or []:
        if not _is_group(obj):
            continue
        lbl = str(getattr(obj, "Label", "") or getattr(obj, "Name", "")).strip().lower()
        if lbl == target:
            return obj
    return None


def _collect_scope_objects(doc, scope_name):
    if scope_name == "Seleccion actual":
        sel = list(Gui.Selection.getSelection() or [])
        out = []
        for obj in sel:
            if _is_group(obj):
                out.extend(list(_iter_group_objects(obj)))
            else:
                out.append(obj)
        return out
    if scope_name == "Grupo Tomacorrientes":
        grp = _find_group_by_label(doc, "Tomacorrientes")
        if grp is None:
            return []
        return list(_iter_group_objects(grp))
    # Documento completo (sin grupos)
    out = []
    for obj in getattr(doc, "Objects", []) or []:
        if _is_group(obj):
            continue
        out.append(obj)
    return out


def _safe_text(v):
    try:
        return str(v or "")
    except Exception:
        return ""


def _obj_key(obj):
    try:
        if hasattr(obj, "KeyRegistro"):
            return _safe_text(getattr(obj, "KeyRegistro")).strip()
    except Exception:
        pass
    return ""


def _is_socket_candidate(obj, classifier):
    label = _safe_text(getattr(obj, "Label", "")).lower()
    name = _safe_text(getattr(obj, "Name", "")).lower()
    if "conexion" in label or "conexion" in name:
        return False
    if "ruta critica" in label or "ruta_critica" in name:
        return False
    if "etiqueta_" in label:
        return False

    if classifier is not None:
        try:
            return classifier.get_component_type(obj) == "Toma"
        except Exception:
            pass
    key = _obj_key(obj).lower()
    if "tomacorriente" in key:
        return True
    if hasattr(obj, "Tipo"):
        try:
            if _safe_text(getattr(obj, "Tipo")).strip().lower() == "toma":
                return True
        except Exception:
            pass
    # fallback estricto: inicio de nombre/label
    return label.startswith("toma") or name.startswith("toma") or label.startswith("tomacorriente")


def _matches_old_key(obj, old_key):
    if not old_key or old_key == "(Cualquiera)":
        return True
    key = _obj_key(obj)
    if key:
        return key == old_key
    # Si no hay KeyRegistro, lo tratamos como legacy y permitimos reemplazo
    return True


def _can_update_in_place(obj):
    if _safe_text(getattr(obj, "TypeId", "")) == "App::Link":
        return False
    return hasattr(obj, "KeyRegistro") and hasattr(obj, "touch")


def _parents_groups(obj):
    parents = []
    for p in (getattr(obj, "InList", []) or []):
        if _is_group(p):
            parents.append(p)
    return parents


def _copy_view_style(src, dst):
    try:
        if hasattr(src, "ViewObject") and hasattr(dst, "ViewObject"):
            dst.ViewObject.ShapeColor = src.ViewObject.ShapeColor
            dst.ViewObject.LineColor = src.ViewObject.LineColor
            dst.ViewObject.PointColor = src.ViewObject.PointColor
            dst.ViewObject.LineWidth = src.ViewObject.LineWidth
            dst.ViewObject.DisplayMode = src.ViewObject.DisplayMode
            dst.ViewObject.Transparency = src.ViewObject.Transparency
    except Exception:
        pass


def _shape_center_world(obj):
    try:
        shp = getattr(obj, "Shape", None)
        if shp is not None and (not shp.isNull()):
            return shp.BoundBox.Center
    except Exception:
        pass
    try:
        if hasattr(obj, "Placement"):
            return obj.Placement.Base
    except Exception:
        pass
    return None


def _shift_object(obj, delta):
    try:
        if delta is None:
            return False
        if delta.Length <= EPS_MM:
            return False
    except Exception:
        return False
    try:
        pl = obj.Placement
        obj.Placement = App.Placement(pl.Base.add(delta), pl.Rotation)
        try:
            obj.touch()
        except Exception:
            pass
        return True
    except Exception:
        try:
            obj.Placement.Base = obj.Placement.Base.add(delta)
            try:
                obj.touch()
            except Exception:
                pass
            return True
        except Exception:
            return False


def _replace_object(doc, module, obj, new_key):
    old_center = _shape_center_world(obj)
    try:
        placement = obj.Placement
    except Exception:
        placement = None
    label = _safe_text(getattr(obj, "Label", ""))
    parents = _parents_groups(obj)
    try:
        old_altura = float(getattr(obj, "AlturaRel")) if hasattr(obj, "AlturaRel") else None
    except Exception:
        old_altura = None
    old_modo = _safe_text(getattr(obj, "ModoVisual", "Ambos")) or "Ambos"
    old_orient = _safe_text(getattr(obj, "OrientacionPared", "Vertical")) or "Vertical"

    new_obj = None
    if hasattr(module, "crear_toma_link"):
        try:
            new_obj = module.crear_toma_link(
                doc=doc,
                name_prefix="Toma_",
                key_registro=new_key,
                tipo_logico="Toma",
                placement=placement,
                modo_visual=old_modo,
                altura_rel=float(old_altura if old_altura is not None else 300.0),
                orientacion_pared=old_orient,
                recompute=False,
            )
        except Exception:
            new_obj = None
    if new_obj is None:
        try:
            new_obj = module.crear_toma_uno(
                doc=doc,
                name_prefix="Toma_",
                key_registro=new_key,
                tipo_logico="Toma",
                recompute=False,
            )
        except TypeError:
            new_obj = module.crear_toma_uno(
                doc=doc,
                name_prefix="Toma_",
                key_registro=new_key,
                tipo_logico="Toma",
            )
        try:
            new_obj.ModoVisual = old_modo
        except Exception:
            pass
        if old_altura is not None:
            try:
                new_obj.AlturaRel = old_altura
            except Exception:
                pass
        try:
            new_obj.OrientacionPared = old_orient
        except Exception:
            pass
        if placement is not None:
            try:
                new_obj.Placement = placement
            except Exception:
                pass
    if label:
        try:
            new_obj.Label = label
        except Exception:
            pass
    _copy_view_style(obj, new_obj)

    # Compensar posibles diferencias de origen entre prototipos.
    new_center = _shape_center_world(new_obj)
    if old_center is not None and new_center is not None:
        delta = old_center.sub(new_center)
        _shift_object(new_obj, delta)

    for g in parents:
        try:
            if new_obj not in (getattr(g, "Group", []) or []):
                g.addObject(new_obj)
        except Exception:
            pass
        try:
            g.removeObject(obj)
        except Exception:
            pass
    try:
        doc.removeObject(obj.Name)
    except Exception:
        pass
    return new_obj


def _ask_items(title, label, items, current=0):
    if not items:
        return None, False
    try:
        value, ok = QtWidgets.QInputDialog.getItem(None, title, label, items, current, False)
        return value, bool(ok)
    except Exception:
        return None, False


def main():
    doc = App.ActiveDocument
    if doc is None:
        _err("No hay documento activo. Abra primero el archivo de FreeCAD.")
        return

    _ensure_paths()
    classifier = _load_classifier()
    module = _load_toma_module()
    toma_keys = _load_toma_keys()
    if not toma_keys:
        _err("No se encontraron claves de tomacorriente en registry_electric.json")
        return

    old_opts = ["(Cualquiera)"] + toma_keys
    old_key, ok = _ask_items(
        "Reemplazar tomacorrientes",
        "Clave actual:",
        old_opts,
        0,
    )
    if not ok:
        return

    new_default = 0
    if old_key in toma_keys:
        for i, k in enumerate(toma_keys):
            if k != old_key:
                new_default = i
                break
    new_key, ok = _ask_items(
        "Reemplazar tomacorrientes",
        "Nueva clave:",
        toma_keys,
        new_default,
    )
    if not ok:
        return

    scope_opts = ["Seleccion actual", "Grupo Tomacorrientes", "Documento completo"]
    scope, ok = _ask_items(
        "Reemplazar tomacorrientes",
        "Alcance:",
        scope_opts,
        1,
    )
    if not ok:
        return

    all_objects = _collect_scope_objects(doc, scope)
    if not all_objects:
        _err(f"No se encontraron objetos en alcance '{scope}'.")
        return

    candidates = []
    seen = set()
    for obj in all_objects:
        if obj is None:
            continue
        key = _safe_text(getattr(obj, "Name", ""))
        if not key or key in seen:
            continue
        seen.add(key)
        if not _is_socket_candidate(obj, classifier):
            continue
        if not _matches_old_key(obj, old_key):
            continue
        candidates.append(obj)

    if not candidates:
        _warn("No hay tomacorrientes que coincidan con el filtro.")
        return

    _log(f"Objetos candidatos: {len(candidates)} | old='{old_key}' -> new='{new_key}' | alcance='{scope}'")
    try:
        doc.openTransaction("Reemplazar tomacorrientes")
    except Exception:
        pass

    updated = 0
    compensated = 0
    replaced = 0
    failed = 0
    pending_comp = []
    for obj in candidates:
        try:
            if _can_update_in_place(obj):
                old_center = _shape_center_world(obj)
                obj.KeyRegistro = new_key
                try:
                    obj.Tipo = "Toma"
                except Exception:
                    pass
                try:
                    obj.touch()
                except Exception:
                    pass
                pending_comp.append((obj, old_center))
                updated += 1
            else:
                _replace_object(doc, module, obj, new_key)
                replaced += 1
        except Exception as ex:
            failed += 1
            _warn(f"Fallo en '{_safe_text(getattr(obj, 'Label', obj.Name))}': {ex}")

    try:
        doc.recompute()
    except Exception as ex:
        _warn(f"Recompute con advertencia: {ex}")

    # Segunda pasada: alinear centros para evitar corrimientos por origen de STEP.
    for obj, old_center in pending_comp:
        try:
            if old_center is None:
                continue
            new_center = _shape_center_world(obj)
            if new_center is None:
                continue
            delta = old_center.sub(new_center)
            if _shift_object(obj, delta):
                compensated += 1
        except Exception:
            pass

    if compensated:
        try:
            doc.recompute()
        except Exception:
            pass
        _log(f"Compensacion aplicada a {compensated} toma(s) para conservar posicion.")

    try:
        doc.commitTransaction()
    except Exception:
        pass

    _log(f"Listo. Actualizados: {updated} | Reemplazados: {replaced} | Compensados: {compensated} | Fallos: {failed}")


if __name__ == "__main__":
    main()

# -*- coding: utf-8 -*-
# MenuText: Registrar acometida y ruta
# Icon: Registrar_Acometida_y_Ruta.svg
# Revision: 2026-08-10 20:31 CST - popup QComboBox legible en Task Panel Qt6.

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()


"""
Macro base para acometida:
- Formulario para capturar datos de acometida.
- Calcula corriente nominal/diseno, breaker y conductor recomendados.
- Crea (o reemplaza) un Draft Wire de ruta desde medidor a tablero principal.
- Guarda historial en Spreadsheet "Acometida" para recalculo en el tiempo.

Notas:
- Version inicial; tablas de ampacidad y criterios son aproximados.
- Ajustar segun NEC/Codigo CR en iteraciones posteriores.
"""

import json
import math
import os
import re
import time
from datetime import datetime

import FreeCAD as App
import FreeCADGui as Gui
import Draft
try:
    import Part
except Exception:
    Part = None

try:
    from PySide2 import QtCore, QtWidgets
except Exception:
    try:
        from PySide import QtCore, QtGui as QtWidgets
    except Exception:
        QtCore = None
        QtWidgets = None


TAG = "[ACOMETIDA]"
BREAKER_STANDARDS = [15, 20, 30, 40, 50, 60, 70, 80, 90, 100, 125, 150, 175, 200, 225, 250, 300, 400, 600]
AWG_ORDER = ["14", "12", "10", "8", "6", "4", "3", "2", "1", "1/0", "2/0", "3/0", "4/0"]

AMPACITY_CU = {
    "14": 20, "12": 25, "10": 35, "8": 50, "6": 65, "4": 85, "3": 100,
    "2": 115, "1": 130, "1/0": 150, "2/0": 175, "3/0": 200, "4/0": 230,
}
AMPACITY_AL = {
    "12": 20, "10": 30, "8": 40, "6": 50, "4": 65, "3": 75,
    "2": 90, "1": 100, "1/0": 120, "2/0": 135, "3/0": 155, "4/0": 180,
}
AWG_CMIL = {
    "14": 4110, "12": 6530, "10": 10380, "8": 16510, "6": 26240, "4": 41740,
    "3": 52620, "2": 66360, "1": 83690, "1/0": 105600, "2/0": 133100,
    "3/0": 167800, "4/0": 211600,
}

STATE_FILE_NAME = "_acometida_state.json"
AREA_LOAD_DEFAULTS = {
    "NEC": 32.29,  # 3 VA/ft2 aproximado
    "CR": 32.29,   # ajustar segun tabla local vigente
}
ACOMETIDA_HEADERS = [
    "Fecha",
    "Medidor",
    "TableroPrincipal",
    "Sistema",
    "Normativa",
    "Metodo_demanda",
    "Carga_base_VA_m2",
    "Area_total_m2",
    "Demanda_kVA_manual",
    "Demanda_kVA_area",
    "Demanda_kVA_usada",
    "Polos",
    "V_LN",
    "V_LL",
    "FP",
    "P_kW",
    "I_nom_A",
    "Crecimiento_pct",
    "I_diseno_A",
    "Material",
    "Breaker_sel_A",
    "Breaker_calc_A",
    "Conductor_sel_AWG",
    "Conductor_calc_AWG",
    "Longitud_ruta_m",
    "Caida_sel_pct",
    "Caida_calc_pct",
    "WireName",
    "Observaciones",
    "Fuente_longitud",
    "Wire_manual",
]


def _log_i(msg):
    App.Console.PrintMessage(f"{TAG}[INFO] {msg}\n")


def _log_w(msg):
    App.Console.PrintWarning(f"{TAG}[WARN] {msg}\n")


def _log_e(msg):
    App.Console.PrintError(f"{TAG}[ERROR] {msg}\n")


def _safe_text(v):
    try:
        return str(v or "")
    except Exception:
        return ""


def _to_float(v, default=0.0):
    try:
        return float(v)
    except Exception:
        pass
    try:
        return float(getattr(v, "Value", default))
    except Exception:
        return default


def _to_int(v, default=0):
    try:
        return int(round(float(v)))
    except Exception:
        return int(default)


def _safe_name(text):
    s = re.sub(r"[^0-9A-Za-z_]+", "_", _safe_text(text))
    s = re.sub(r"_+", "_", s).strip("_")
    return s or "Obj"


def _default_va_m2(norma):
    key = _safe_text(norma).strip().upper()
    if key in AREA_LOAD_DEFAULTS:
        return _to_float(AREA_LOAD_DEFAULTS[key], 32.29)
    return 32.29


def _state_path():
    try:
        base = os.path.dirname(os.path.abspath(__file__))
    except Exception:
        base = os.getcwd()
    return os.path.join(base, STATE_FILE_NAME)


def _load_state():
    path = _state_path()
    try:
        if os.path.exists(path):
            with open(path, "r", encoding="utf-8") as f:
                data = json.load(f)
            return data if isinstance(data, dict) else {}
    except Exception as ex:
        _log_w(f"No se pudo leer estado previo: {ex}")
    return {}


def _save_state(data):
    path = _state_path()
    try:
        payload = data if isinstance(data, dict) else {}
        with open(path, "w", encoding="utf-8") as f:
            json.dump(payload, f, ensure_ascii=False, indent=2)
    except Exception as ex:
        _log_w(f"No se pudo guardar estado: {ex}")


def _col_letter(idx):
    out = ""
    i = int(idx)
    while i > 0:
        i, rem = divmod(i - 1, 26)
        out = chr(65 + rem) + out
    return out or "A"


def _set_text(sheet, cell, value):
    # Always force text to avoid Spreadsheet expression parsing (example: "2/0").
    s = _safe_text(value).replace('"', '""')
    sheet.set(cell, '"' + s + '"')


def _set_number(sheet, cell, value, decimals=2):
    try:
        sheet.set(cell, f"{float(value):.{decimals}f}")
    except Exception:
        sheet.set(cell, "")


def _get_cell(sheet, cell, default=""):
    try:
        v = sheet.get(cell)
        return v if v is not None else default
    except Exception:
        return default


def _get_raw_cell(sheet, cell, default=""):
    try:
        if hasattr(sheet, "getContents"):
            v = sheet.getContents(cell)
            return v if v is not None else default
    except Exception:
        pass
    return _get_cell(sheet, cell, default)


def _first_empty_row(sheet, used_cols, start_row=2, max_rows=20000):
    for r in range(start_row, max_rows + 1):
        empty = True
        for c in used_cols:
            v = _safe_text(_get_cell(sheet, f"{c}{r}", "")).strip()
            if v:
                empty = False
                break
        if empty:
            return r
    return max_rows + 1


def _repair_legacy_awg_cells(sheet, max_rows=5000):
    # Repair old cells where values like 2/0 were interpreted as expression.
    for c in range(1, 60):
        col = _col_letter(c)
        for r in range(2, max_rows + 1):
            cell = f"{col}{r}"
            raw = _safe_text(_get_raw_cell(sheet, cell, "")).strip()
            if not raw:
                continue
            cleaned = raw.strip().strip('"').replace(" ", "")
            if re.match(r"^\d+/0$", cleaned):
                _set_text(sheet, cell, cleaned)


def _ensure_sheet(doc, name="Acometida"):
    sheet = doc.getObject(name)
    if sheet is None:
        sheet = doc.addObject("Spreadsheet::Sheet", name)

    for i, h in enumerate(ACOMETIDA_HEADERS, start=1):
        _set_text(sheet, f"{_col_letter(i)}1", h)
    _repair_legacy_awg_cells(sheet, max_rows=5000)

    used = [_col_letter(i) for i in range(1, len(ACOMETIDA_HEADERS) + 1)]
    return sheet, used


def _connection_point(obj):
    if obj is None or not hasattr(obj, "Placement"):
        return App.Vector(0, 0, 0)
    p = obj.Placement.Base
    z_extra = 0.0
    for n in ("AlturaRel", "Altura", "Elevation", "Elevacion", "Z"):
        if hasattr(obj, n):
            try:
                z_extra = _to_float(getattr(obj, n), 0.0)
                break
            except Exception:
                pass
    return App.Vector(_to_float(p.x, 0.0), _to_float(p.y, 0.0), _to_float(p.z, 0.0) + z_extra)


def _route_points_ortho(p0, p1, z_route):
    z = max(_to_float(z_route, 0.0), _to_float(p0.z, 0.0), _to_float(p1.z, 0.0))
    pts = [
        App.Vector(p0.x, p0.y, p0.z),
        App.Vector(p0.x, p0.y, z),
        App.Vector(p1.x, p0.y, z),
        App.Vector(p1.x, p1.y, z),
        App.Vector(p1.x, p1.y, p1.z),
    ]
    clean = []
    for p in pts:
        if not clean:
            clean.append(p)
            continue
        if p.distanceToPoint(clean[-1]) > 1e-7:
            clean.append(p)
    return clean


def _path_length_mm(points):
    total = 0.0
    if not points or len(points) < 2:
        return total
    for i in range(1, len(points)):
        total += points[i - 1].distanceToPoint(points[i])
    return total


def _make_wire(points):
    maker = getattr(Draft, "make_wire", None)
    if maker is None:
        maker = getattr(Draft, "makeWire", None)
    if maker is None:
        raise RuntimeError("No se encontro Draft.make_wire ni Draft.makeWire")

    attempts = [
        lambda: maker(points, closed=False, face=False),
        lambda: maker(points, False, False),
        lambda: maker(points, False),
        lambda: maker(points),
    ]
    last_err = None
    for attempt in attempts:
        try:
            return attempt()
        except Exception as ex:
            last_err = ex
    raise RuntimeError(f"No se pudo crear Wire: {last_err}")


def _ensure_group(doc, group_name):
    g = doc.getObject(group_name)
    if g is None:
        g = doc.addObject("App::DocumentObjectGroup", group_name)
    return g


def _add_to_group_safe(group_obj, child_obj):
    if group_obj is None or child_obj is None:
        return
    try:
        current = list(getattr(group_obj, "Group", []) or [])
        if child_obj in current:
            return
    except Exception:
        pass
    try:
        group_obj.addObject(child_obj)
    except Exception:
        pass


def _next_breaker(amps):
    a = _to_float(amps, 0.0)
    if a <= 0:
        return 15
    for b in BREAKER_STANDARDS:
        if a <= float(b):
            return int(b)
    return int(BREAKER_STANDARDS[-1])


def _ampacity_table(material):
    m = _safe_text(material).strip().lower()
    return AMPACITY_AL if m.startswith("al") else AMPACITY_CU


def _awg_for_current(material, required_amps):
    req = _to_float(required_amps, 0.0)
    table = _ampacity_table(material)
    for awg in AWG_ORDER:
        if awg in table and _to_float(table[awg], 0.0) >= req:
            return awg
    return AWG_ORDER[-1]


def _cmil_from_awg(awg):
    key = _safe_text(awg).strip().upper()
    return _to_float(AWG_CMIL.get(key, 0.0), 0.0)


def _voltage_drop_pct(distance_m, current_a, voltage_v, poles, awg):
    d = _to_float(distance_m, 0.0)
    i = _to_float(current_a, 0.0)
    v = _to_float(voltage_v, 0.0)
    cmil = _cmil_from_awg(awg)
    if d <= 0 or i <= 0 or v <= 0 or cmil <= 0:
        return 0.0

    # Copper approximation. For first version this is used for both Cu/Al as estimate.
    k = 12.9
    l_ft = d * 3.28084
    p = _to_int(poles, 2)
    if p >= 3:
        v_drop = (1.732 * k * i * l_ft) / cmil
    else:
        v_drop = (2.0 * k * i * l_ft) / cmil
    return (v_drop / v) * 100.0


def _shape_length_mm(obj):
    if obj is None or not hasattr(obj, "Shape"):
        return 0.0
    try:
        sh = obj.Shape
    except Exception:
        return 0.0
    if sh is None:
        return 0.0
    try:
        length_attr = getattr(sh, "Length", 0.0)
    except Exception:
        length_attr = 0.0
    length = _to_float(length_attr, 0.0)
    if length > 0:
        return length
    total = 0.0
    try:
        for e in getattr(sh, "Edges", []) or []:
            try:
                elen = getattr(e, "Length", 0.0)
            except Exception:
                elen = 0.0
            total += _to_float(elen, 0.0)
    except Exception:
        pass
    return total


def _area_to_m2(value, assume_mm2=False):
    if value is None:
        return 0.0
    try:
        if hasattr(value, "getValueAs"):
            q = value.getValueAs("m^2")
            return max(_to_float(q, 0.0), 0.0)
    except Exception:
        pass
    num = _to_float(getattr(value, "Value", value), 0.0)
    if num <= 0:
        return 0.0
    if assume_mm2:
        return num / 1000000.0
    if hasattr(value, "Unit"):
        # Fallback for quantities without getValueAs.
        return num / 1000000.0
    # Plain numeric fallback:
    # - if very large, likely mm2
    # - otherwise treat as m2
    if num > 10000.0:
        return num / 1000000.0
    return num


def _to_vec3(v):
    if v is None:
        return None
    try:
        return App.Vector(_to_float(v.x, 0.0), _to_float(v.y, 0.0), _to_float(v.z, 0.0))
    except Exception:
        pass
    try:
        if len(v) >= 3:
            return App.Vector(_to_float(v[0], 0.0), _to_float(v[1], 0.0), _to_float(v[2], 0.0))
    except Exception:
        pass
    return None


def _polygon_area_m2(points, is_closed=False):
    if not points or len(points) < 3:
        return 0.0
    pts = []
    for p in points:
        v = _to_vec3(p)
        if v is not None:
            pts.append(v)
    if len(pts) < 3:
        return 0.0

    # Wire must be closed to define area.
    geom_closed = pts[0].distanceToPoint(pts[-1]) <= 1e-6
    if not is_closed and not geom_closed:
        return 0.0

    pts2 = pts[:-1] if geom_closed else pts[:]
    if len(pts2) < 3:
        return 0.0

    acc = App.Vector(0.0, 0.0, 0.0)
    n = len(pts2)
    for i in range(n):
        p0 = pts2[i]
        p1 = pts2[(i + 1) % n]
        acc = acc.add(p0.cross(p1))
    area_mm2 = 0.5 * acc.Length
    if area_mm2 <= 0:
        return 0.0
    return area_mm2 / 1000000.0


def _shape_area_m2(obj, _visited=None):
    if obj is None:
        return 0.0

    if _visited is None:
        _visited = set()
    name = _safe_text(getattr(obj, "Name", ""))
    if name:
        if name in _visited:
            return 0.0
        _visited.add(name)

    # If obj is a Link, evaluate linked object area.
    linked = getattr(obj, "LinkedObject", None)
    if linked is not None:
        a_link = _shape_area_m2(linked, _visited)
        if a_link > 0:
            return a_link

    # If obj is a Group, sum area of children.
    if hasattr(obj, "Group"):
        total = 0.0
        try:
            for child in list(getattr(obj, "Group", []) or []):
                total += _shape_area_m2(child, _visited)
        except Exception:
            pass
        if total > 0:
            return total

    # Prefer direct Area property when available.
    if hasattr(obj, "Area"):
        try:
            a = _area_to_m2(getattr(obj, "Area"), assume_mm2=False)
            if a > 0:
                return a
        except Exception:
            pass

    sh = None
    if hasattr(obj, "Shape"):
        try:
            sh = obj.Shape
        except Exception:
            sh = None

    if sh is not None:
        # Shape.Area in FreeCAD geometry is usually mm2.
        try:
            a = _area_to_m2(getattr(sh, "Area", 0.0), assume_mm2=True)
            if a > 0:
                return a
        except Exception:
            pass

        # Try to create face from closed wires if area is not directly available.
        if Part is not None:
            try:
                for w in list(getattr(sh, "Wires", []) or []):
                    try:
                        if not w.isClosed():
                            continue
                        face = Part.Face(w)
                        a = _area_to_m2(getattr(face, "Area", 0.0), assume_mm2=True)
                        if a > 0:
                            return a
                    except Exception:
                        continue
            except Exception:
                pass

    # Last fallback: polygon area from Draft points (closed wire).
    points = getattr(obj, "Points", None)
    if points:
        try:
            closed_flag = bool(getattr(obj, "Closed", False))
            return _polygon_area_m2(points, is_closed=closed_flag)
        except Exception:
            pass
    return 0.0


def _is_wire_like_object(obj):
    if obj is None:
        return False
    t = _safe_text(getattr(obj, "TypeId", "")).lower()
    if "wire" in t:
        return True
    if hasattr(obj, "Points"):
        return True
    try:
        sh = getattr(obj, "Shape", None)
        if sh is not None:
            edges = len(list(getattr(sh, "Edges", []) or []))
            faces = len(list(getattr(sh, "Faces", []) or []))
            if edges > 0 and faces == 0:
                return True
    except Exception:
        pass
    return False


def _is_closed_object(obj):
    if obj is None:
        return False
    try:
        if bool(getattr(obj, "Closed", False)):
            return True
    except Exception:
        pass
    points = getattr(obj, "Points", None)
    if points:
        pts = []
        for p in points:
            v = _to_vec3(p)
            if v is not None:
                pts.append(v)
        if len(pts) >= 3 and pts[0].distanceToPoint(pts[-1]) <= 1e-6:
            return True
    try:
        sh = getattr(obj, "Shape", None)
        if sh is not None:
            if len(list(getattr(sh, "Faces", []) or [])) > 0:
                return True
            for w in list(getattr(sh, "Wires", []) or []):
                if w.isClosed():
                    return True
    except Exception:
        pass
    return False


def _candidate_objects(doc):
    out = []
    for obj in getattr(doc, "Objects", []) or []:
        if not hasattr(obj, "Placement"):
            continue
        if hasattr(obj, "Group"):
            continue
        out.append(obj)
    out.sort(key=lambda o: (_safe_text(getattr(o, "Label", "")).lower(), _safe_text(getattr(o, "Name", "")).lower()))
    return out


def _candidate_wires(doc):
    out = []
    for obj in getattr(doc, "Objects", []) or []:
        try:
            t = _safe_text(getattr(obj, "TypeId", "")).lower()
            if "wire" in t:
                out.append(obj)
                continue
            if hasattr(obj, "Shape"):
                if _shape_length_mm(obj) > 0:
                    out.append(obj)
        except Exception:
            # Ignore objects with broken/incomplete shapes.
            continue
    # unique by Name preserving order
    seen = set()
    uniq = []
    for o in out:
        n = _safe_text(getattr(o, "Name", ""))
        if n in seen:
            continue
        seen.add(n)
        uniq.append(o)
    uniq.sort(key=lambda o: (_safe_text(getattr(o, "Label", "")).lower(), _safe_text(getattr(o, "Name", "")).lower()))
    return uniq


def _candidate_area_objects(doc):
    out = []
    for obj in getattr(doc, "Objects", []) or []:
        try:
            if _shape_area_m2(obj) > 0:
                out.append(obj)
        except Exception:
            continue
    out.sort(key=lambda o: (_safe_text(getattr(o, "Label", "")).lower(), _safe_text(getattr(o, "Name", "")).lower()))
    return out


def _acometida_form_qss():
    return """
QWidget#AcometidaRoot {
    background: #f4f7fb;
}
QGroupBox {
    border: 1px solid #c8d2e1;
    border-radius: 8px;
    margin-top: 12px;
    background: #ffffff;
    font-weight: 600;
}
QGroupBox::title {
    subcontrol-origin: margin;
    left: 10px;
    padding: 0 4px 0 4px;
    color: #1d3d6b;
}
QTabWidget::pane {
    border: 1px solid #b7c6da;
    border-radius: 8px;
    background: #ffffff;
}
QWidget#AcometidaTabPage {
    background: #ffffff;
    color: #1f2d3d;
}
QTabBar::tab {
    background: #dfe8f5;
    color: #274661;
    border: 1px solid #b7c6da;
    border-bottom: none;
    border-top-left-radius: 6px;
    border-top-right-radius: 6px;
    min-width: 110px;
    padding: 6px 10px;
    margin-right: 2px;
}
QTabBar::tab:selected {
    background: #ffffff;
    color: #1b4577;
}
QTabBar::tab:disabled {
    background: #e8edf3;
    color: #7a8694;
}
QLabel {
    color: #1f2d3d;
    background: transparent;
}
QCheckBox {
    color: #1f2d3d;
    background: transparent;
}
QCheckBox:disabled {
    color: #7a8694;
}
QPushButton {
    background: #2d6fb8;
    color: white;
    border-radius: 5px;
    padding: 5px 10px;
}
QPushButton:hover {
    background: #255f9d;
}
QComboBox, QDoubleSpinBox, QSpinBox, QLineEdit {
    border: 1px solid #b7c6da;
    border-radius: 4px;
    padding: 2px 4px;
    background: #ffffff;
    color: #1f2d3d;
    selection-background-color: #2d6fb8;
    selection-color: #ffffff;
}
QComboBox:disabled, QDoubleSpinBox:disabled, QSpinBox:disabled, QLineEdit:disabled {
    background: #e8edf3;
    color: #6f7b88;
    border-color: #cbd4df;
}
QComboBox QAbstractItemView {
    background: #ffffff;
    color: #1f2d3d;
    border: 1px solid #b7c6da;
    selection-background-color: #2d6fb8;
    selection-color: #ffffff;
    outline: 0;
}
QComboBox QAbstractItemView::item:selected {
    background: #2d6fb8;
    color: #ffffff;
}
"""


def _acometida_combo_popup_qss():
    """Style the separate Qt6 popup view, which may leave the Task Panel tree."""
    return """
QAbstractItemView#AcometidaComboPopup {
    background-color: #ffffff;
    alternate-background-color: #f4f7fb;
    color: #1f2d3d;
    border: 1px solid #b7c6da;
    selection-background-color: #2d6fb8;
    selection-color: #ffffff;
    outline: 0;
}
QAbstractItemView#AcometidaComboPopup::item {
    background-color: #ffffff;
    color: #1f2d3d;
    min-height: 20px;
    padding: 2px 4px;
}
QAbstractItemView#AcometidaComboPopup::item:selected {
    background-color: #2d6fb8;
    color: #ffffff;
}
QAbstractItemView#AcometidaComboPopup::item:disabled {
    background-color: #e8edf3;
    color: #6f7b88;
}
"""


def _style_acometida_combo_popup(combo):
    """Apply popup colors directly so reparenting into Gui.Control cannot lose them."""
    try:
        view = combo.view()
        view.setObjectName("AcometidaComboPopup")
        view.setStyleSheet(_acometida_combo_popup_qss())
        try:
            viewport = view.viewport()
            viewport.setObjectName("AcometidaComboPopupViewport")
            viewport.setStyleSheet("background-color: #ffffff; color: #1f2d3d;")
        except Exception:
            pass
        return view
    except Exception as ex:
        _log_w("No se pudo aplicar estilo directo al popup de un combo: {}".format(ex))
        return None


class _AcometidaDialog(QtWidgets.QWidget):
    def __init__(self, doc, parent=None):
        super(_AcometidaDialog, self).__init__(parent)
        self.doc = doc
        self.items = _candidate_objects(doc)
        self.wire_items = _candidate_wires(doc)
        self.area_items = _candidate_area_objects(doc)
        self.state = _load_state()
        self.setObjectName("AcometidaRoot")
        self.setMinimumWidth(620)
        self.setStyleSheet(_acometida_form_qss())

        vbox = QtWidgets.QVBoxLayout(self)

        self.cb_medidor = QtWidgets.QComboBox()
        self.cb_tablero = QtWidgets.QComboBox()
        for obj in self.items:
            txt = f"{_safe_text(getattr(obj, 'Label', obj.Name))} ({obj.Name})"
            self.cb_medidor.addItem(txt, obj.Name)
            self.cb_tablero.addItem(txt, obj.Name)

        self.cb_wire_manual = QtWidgets.QComboBox()
        self.cb_wire_manual.addItem("(Auto - crear ruta)", "")
        for obj in self.wire_items:
            txt = f"{_safe_text(getattr(obj, 'Label', obj.Name))} ({obj.Name})"
            self.cb_wire_manual.addItem(txt, obj.Name)

        self.cb_area_obj = QtWidgets.QComboBox()
        self.cb_area_obj.addItem("(Ninguno)", "")
        for obj in self.area_items:
            a = _shape_area_m2(obj)
            txt = f"{_safe_text(getattr(obj, 'Label', obj.Name))} ({obj.Name}) [{a:.3f} m2]"
            self.cb_area_obj.addItem(txt, obj.Name)

        self.cb_system = QtWidgets.QComboBox()
        self.cb_system.addItems(["1F-2H 120/240", "3F-4H 120/208", "3F-4H 277/480"])
        self.cb_norma = QtWidgets.QComboBox()
        self.cb_norma.addItems(["CR", "NEC"])
        self.cb_demanda_metodo = QtWidgets.QComboBox()
        self.cb_demanda_metodo.addItem("Manual (VA)", "MANUAL")
        self.cb_demanda_metodo.addItem("Por area (VA/m2)", "AREA")
        self.cb_demanda_metodo.addItem("Mayor (manual/area)", "MAYOR")

        self.sp_va_m2 = QtWidgets.QDoubleSpinBox()
        self.sp_va_m2.setRange(0.0, 10000.0)
        self.sp_va_m2.setDecimals(3)
        self.sp_va_m2.setValue(_default_va_m2("CR"))

        self.sp_vln = QtWidgets.QDoubleSpinBox()
        self.sp_vln.setRange(0.0, 1000.0)
        self.sp_vln.setDecimals(1)
        self.sp_vln.setValue(120.0)

        self.sp_vll = QtWidgets.QDoubleSpinBox()
        self.sp_vll.setRange(0.0, 1000.0)
        self.sp_vll.setDecimals(1)
        self.sp_vll.setValue(240.0)

        self.sp_demanda_va = QtWidgets.QDoubleSpinBox()
        self.sp_demanda_va.setRange(0.0, 100000000.0)
        self.sp_demanda_va.setDecimals(1)
        self.sp_demanda_va.setSingleStep(100.0)
        self.sp_demanda_va.setValue(25000.0)

        self.sp_pf = QtWidgets.QDoubleSpinBox()
        self.sp_pf.setRange(0.10, 1.00)
        self.sp_pf.setSingleStep(0.01)
        self.sp_pf.setDecimals(2)
        self.sp_pf.setValue(0.95)

        self.sp_growth = QtWidgets.QDoubleSpinBox()
        self.sp_growth.setRange(0.0, 300.0)
        self.sp_growth.setDecimals(1)
        self.sp_growth.setValue(25.0)

        self.sp_breaker = QtWidgets.QSpinBox()
        self.sp_breaker.setRange(0, 6000)
        self.sp_breaker.setValue(100)

        self.cb_material = QtWidgets.QComboBox()
        self.cb_material.addItems(["Cu", "Al"])

        self.cb_awg = QtWidgets.QComboBox()
        self.cb_awg.addItems(AWG_ORDER)
        self.cb_awg.setCurrentText("2")

        self.lb_demanda_area = QtWidgets.QLabel("0.0 VA (0.000 kVA)")
        self.lb_demanda_usada = QtWidgets.QLabel("0.0 VA (0.000 kVA)")
        self.lb_i_nom = QtWidgets.QLabel("0.000 A")
        self.lb_i_diseno = QtWidgets.QLabel("0.000 A")
        self.lb_breaker_calc = QtWidgets.QLabel("-")
        self.lb_conductor_calc = QtWidgets.QLabel("-")
        self.lb_va_breaker_nom = QtWidgets.QLabel("0.0 VA")
        self.lb_va_conductor_nom = QtWidgets.QLabel("0.0 VA")

        self.sp_zroute = QtWidgets.QDoubleSpinBox()
        self.sp_zroute.setRange(-10000.0, 100000.0)
        self.sp_zroute.setDecimals(1)
        self.sp_zroute.setValue(2500.0)

        self.chk_use_manual_wire = QtWidgets.QCheckBox("Usar wire manual para longitud/calculo")
        self.chk_use_manual_wire.setChecked(False)

        self.chk_reuse = QtWidgets.QCheckBox("Reemplazar wire anterior de esta misma acometida")
        self.chk_reuse.setChecked(True)
        self.chk_project_group = QtWidgets.QCheckBox("Crear/usar grupo Proyecto_Acometida")
        self.chk_project_group.setChecked(True)

        self.sp_area_total = QtWidgets.QDoubleSpinBox()
        self.sp_area_total.setRange(0.0, 1000000.0)
        self.sp_area_total.setDecimals(3)
        self.sp_area_total.setValue(0.0)

        self.ed_notes = QtWidgets.QLineEdit()
        self.ed_notes.setPlaceholderText("Notas u observaciones")

        gb_basicos = QtWidgets.QGroupBox("Datos basicos")
        form_basicos = QtWidgets.QFormLayout(gb_basicos)
        form_basicos.addRow("Medidor:", self.cb_medidor)
        form_basicos.addRow("Tablero principal:", self.cb_tablero)
        form_basicos.addRow("Wire ruta manual:", self.cb_wire_manual)
        form_basicos.addRow("", self.chk_use_manual_wire)
        form_basicos.addRow("Altura ruta Z (mm):", self.sp_zroute)
        form_basicos.addRow("Area total proyecto (m2):", self.sp_area_total)
        form_basicos.addRow("Objeto area proyecto:", self.cb_area_obj)
        form_basicos.addRow("", self.chk_project_group)
        form_basicos.addRow("", self.chk_reuse)
        form_basicos.addRow("Observaciones:", self.ed_notes)

        gb_auto = QtWidgets.QGroupBox("Datos calculados por demanda (auto NEC/CR)")
        form_auto = QtWidgets.QFormLayout(gb_auto)
        form_auto.addRow("Sistema:", self.cb_system)
        form_auto.addRow("Voltaje L-N (V):", self.sp_vln)
        form_auto.addRow("Voltaje L-L (V):", self.sp_vll)
        form_auto.addRow("Normativa:", self.cb_norma)
        form_auto.addRow("Metodo demanda:", self.cb_demanda_metodo)
        form_auto.addRow("Carga base (VA/m2):", self.sp_va_m2)
        form_auto.addRow("Demanda manual (VA):", self.sp_demanda_va)
        form_auto.addRow("Demanda area auto:", self.lb_demanda_area)
        form_auto.addRow("Demanda usada:", self.lb_demanda_usada)
        form_auto.addRow("Factor de potencia:", self.sp_pf)
        form_auto.addRow("Crecimiento (%):", self.sp_growth)
        form_auto.addRow("I nominal estimada:", self.lb_i_nom)
        form_auto.addRow("I diseno estimada:", self.lb_i_diseno)
        form_auto.addRow("Breaker calculado:", self.lb_breaker_calc)
        form_auto.addRow("Conductor calculado:", self.lb_conductor_calc)

        gb_manual = QtWidgets.QGroupBox("Seleccion manual final")
        form_manual = QtWidgets.QFormLayout(gb_manual)
        form_manual.addRow("Breaker seleccionado (A):", self.sp_breaker)
        form_manual.addRow("Material conductor:", self.cb_material)
        form_manual.addRow("Conductor seleccionado (AWG):", self.cb_awg)
        form_manual.addRow("VA nominal breaker:", self.lb_va_breaker_nom)
        form_manual.addRow("VA nominal conductor:", self.lb_va_conductor_nom)

        sel_box = QtWidgets.QGroupBox("Seleccion con ventana abierta")
        sel_grid = QtWidgets.QGridLayout(sel_box)
        self.btn_pick_medidor = QtWidgets.QPushButton("Tomar seleccion -> Medidor")
        self.btn_pick_tablero = QtWidgets.QPushButton("Tomar seleccion -> Tablero")
        self.btn_pick_wire_manual = QtWidgets.QPushButton("Tomar seleccion -> Wire manual")
        self.btn_pick_area = QtWidgets.QPushButton("Tomar seleccion -> Area proyecto")
        self.btn_refresh = QtWidgets.QPushButton("Refrescar listas")
        sel_grid.addWidget(self.btn_pick_medidor, 0, 0)
        sel_grid.addWidget(self.btn_pick_tablero, 0, 1)
        sel_grid.addWidget(self.btn_pick_wire_manual, 1, 0)
        sel_grid.addWidget(self.btn_pick_area, 1, 1)
        sel_grid.addWidget(self.btn_refresh, 2, 0, 1, 2)

        tabs = QtWidgets.QTabWidget()
        tab_basicos = QtWidgets.QWidget()
        tab_basicos.setObjectName("AcometidaTabPage")
        lay_basicos = QtWidgets.QVBoxLayout(tab_basicos)
        lay_basicos.addWidget(gb_basicos)
        lay_basicos.addWidget(sel_box)
        lay_basicos.addStretch(1)

        tab_auto = QtWidgets.QWidget()
        tab_auto.setObjectName("AcometidaTabPage")
        lay_auto = QtWidgets.QVBoxLayout(tab_auto)
        lay_auto.addWidget(gb_auto)
        lay_auto.addStretch(1)

        tab_manual = QtWidgets.QWidget()
        tab_manual.setObjectName("AcometidaTabPage")
        lay_manual = QtWidgets.QVBoxLayout(tab_manual)
        lay_manual.addWidget(gb_manual)
        lay_manual.addStretch(1)

        tabs.addTab(tab_basicos, "Datos Basicos")
        tabs.addTab(tab_auto, "Demanda Auto")
        tabs.addTab(tab_manual, "Seleccion Final")
        vbox.addWidget(tabs)

        # QComboBox creates its list as a separate popup. In FreeCAD's Qt6
        # Task Panel that popup may be reparented outside AcometidaRoot and no
        # longer inherit its light QSS, so style each native view directly.
        self._acometida_combo_popup_views = []
        for combo in self.findChildren(QtWidgets.QComboBox):
            view = _style_acometida_combo_popup(combo)
            if view is not None:
                self._acometida_combo_popup_views.append(view)

        self.cb_system.currentIndexChanged.connect(self._apply_system_defaults)
        self.cb_norma.currentIndexChanged.connect(self._on_norma_changed)
        self.cb_area_obj.currentIndexChanged.connect(self._on_area_obj_changed)
        self.cb_wire_manual.currentIndexChanged.connect(self._on_manual_wire_changed)
        self.cb_demanda_metodo.currentIndexChanged.connect(self._update_preview)
        self.sp_va_m2.valueChanged.connect(self._update_preview)
        self.sp_demanda_va.valueChanged.connect(self._update_preview)
        self.sp_vln.valueChanged.connect(self._update_preview)
        self.sp_vll.valueChanged.connect(self._update_preview)
        self.sp_pf.valueChanged.connect(self._update_preview)
        self.sp_growth.valueChanged.connect(self._update_preview)
        self.sp_area_total.valueChanged.connect(self._update_preview)
        self.sp_breaker.valueChanged.connect(self._update_preview)
        self.cb_material.currentIndexChanged.connect(self._update_preview)
        self.cb_awg.currentIndexChanged.connect(self._update_preview)
        self.btn_pick_medidor.clicked.connect(lambda: self._assign_from_selection("medidor"))
        self.btn_pick_tablero.clicked.connect(lambda: self._assign_from_selection("tablero"))
        self.btn_pick_wire_manual.clicked.connect(lambda: self._assign_from_selection("wire_manual"))
        self.btn_pick_area.clicked.connect(lambda: self._assign_from_selection("area_obj"))
        self.btn_refresh.clicked.connect(self._refresh_dynamic_lists)
        self._apply_system_defaults()
        self._on_norma_changed()
        self._apply_state_defaults()
        self._prefill_from_selection()
        self._update_preview()

    def _prefill_from_selection(self):
        sel = list(Gui.Selection.getSelection() or [])
        if len(sel) >= 1:
            self._set_combo_obj(self.cb_medidor, sel[0])
        if len(sel) >= 2:
            self._set_combo_obj(self.cb_tablero, sel[1])
        if len(sel) >= 3:
            self._set_combo_obj(self.cb_wire_manual, sel[2])
            self.chk_use_manual_wire.setChecked(True)
        if len(sel) >= 4:
            self._set_combo_obj(self.cb_area_obj, sel[3])
            self._on_area_obj_changed()
        self._update_preview()

    def _set_combo_obj(self, combo, obj):
        if obj is None:
            return
        name = _safe_text(getattr(obj, "Name", ""))
        self._set_combo_name(combo, name)

    def _set_combo_name(self, combo, name):
        if not name:
            return
        for i in range(combo.count()):
            if _safe_text(combo.itemData(i)) == name:
                combo.setCurrentIndex(i)
                return

    def _obj_display_text(self, obj, with_area=False):
        base = f"{_safe_text(getattr(obj, 'Label', obj.Name))} ({obj.Name})"
        if with_area:
            a = _shape_area_m2(obj)
            return f"{base} [{a:.3f} m2]"
        return base

    def _ensure_combo_has_object(self, combo, obj, with_area=False):
        if obj is None:
            return
        name = _safe_text(getattr(obj, "Name", "")).strip()
        if not name:
            return
        for i in range(combo.count()):
            if _safe_text(combo.itemData(i)).strip() == name:
                combo.setCurrentIndex(i)
                return
        combo.addItem(self._obj_display_text(obj, with_area=with_area), name)
        combo.setCurrentIndex(combo.count() - 1)

    def _current_selection_object(self):
        sel = list(Gui.Selection.getSelection() or [])
        if sel:
            return sel[0]
        try:
            sx = list(Gui.Selection.getSelectionEx() or [])
            for s in sx:
                obj = getattr(s, "Object", None)
                if obj is not None:
                    return obj
        except Exception:
            pass
        return None

    def _assign_from_selection(self, target):
        obj = self._current_selection_object()
        if obj is None:
            _log_w("No hay seleccion activa para capturar.")
            return
        if target == "medidor":
            self._ensure_combo_has_object(self.cb_medidor, obj, with_area=False)
            return
        if target == "tablero":
            self._ensure_combo_has_object(self.cb_tablero, obj, with_area=False)
            return
        if target == "wire_manual":
            self._ensure_combo_has_object(self.cb_wire_manual, obj, with_area=False)
            self.chk_use_manual_wire.setChecked(True)
            return
        if target == "area_obj":
            self._ensure_combo_has_object(self.cb_area_obj, obj, with_area=True)
            self._on_area_obj_changed()
            return

    def _refresh_dynamic_lists(self):
        cur_wire_manual = _safe_text(self.cb_wire_manual.currentData()).strip()
        cur_area_obj = _safe_text(self.cb_area_obj.currentData()).strip()

        self.wire_items = _candidate_wires(self.doc)
        self.area_items = _candidate_area_objects(self.doc)

        self.cb_wire_manual.clear()
        self.cb_wire_manual.addItem("(Auto - crear ruta)", "")
        for obj in self.wire_items:
            self.cb_wire_manual.addItem(self._obj_display_text(obj, with_area=False), obj.Name)

        self.cb_area_obj.clear()
        self.cb_area_obj.addItem("(Ninguno)", "")
        for obj in self.area_items:
            self.cb_area_obj.addItem(self._obj_display_text(obj, with_area=True), obj.Name)

        self._set_combo_name(self.cb_wire_manual, cur_wire_manual)
        self._set_combo_name(self.cb_area_obj, cur_area_obj)
        self._update_preview()

    def _apply_state_defaults(self):
        st = self.state or {}
        self._set_combo_name(self.cb_medidor, _safe_text(st.get("medidor_name")))
        self._set_combo_name(self.cb_tablero, _safe_text(st.get("tablero_name")))
        self._set_combo_name(self.cb_wire_manual, _safe_text(st.get("wire_manual_name")))
        self._set_combo_name(self.cb_area_obj, _safe_text(st.get("area_obj_name")))
        if _safe_text(st.get("sistema")):
            idx = self.cb_system.findText(_safe_text(st.get("sistema")))
            if idx >= 0:
                self.cb_system.setCurrentIndex(idx)
        normativa = _safe_text(st.get("normativa")).strip().upper()
        if normativa in AREA_LOAD_DEFAULTS:
            self.cb_norma.setCurrentText(normativa)
        demand_method = _safe_text(st.get("demand_method")).strip().upper()
        if demand_method:
            idx = self.cb_demanda_metodo.findData(demand_method)
            if idx >= 0:
                self.cb_demanda_metodo.setCurrentIndex(idx)
        if _to_float(st.get("carga_base_va_m2"), -1.0) >= 0:
            self.sp_va_m2.setValue(_to_float(st.get("carga_base_va_m2"), self.sp_va_m2.value()))
        if _to_float(st.get("demanda_va_manual"), -1.0) >= 0:
            self.sp_demanda_va.setValue(_to_float(st.get("demanda_va_manual"), self.sp_demanda_va.value()))
        elif _to_float(st.get("demanda_kva"), -1.0) >= 0:
            self.sp_demanda_va.setValue(_to_float(st.get("demanda_kva"), 0.0) * 1000.0)
        if _to_float(st.get("pf"), -1.0) > 0:
            self.sp_pf.setValue(_to_float(st.get("pf"), self.sp_pf.value()))
        if _to_float(st.get("growth_pct"), -1.0) >= 0:
            self.sp_growth.setValue(_to_float(st.get("growth_pct"), self.sp_growth.value()))
        if _to_int(st.get("breaker_sel"), -1) >= 0:
            self.sp_breaker.setValue(_to_int(st.get("breaker_sel"), self.sp_breaker.value()))
        if _to_float(st.get("z_route_mm"), -1.0) > -1.0:
            self.sp_zroute.setValue(_to_float(st.get("z_route_mm"), self.sp_zroute.value()))
        if _to_float(st.get("area_total_m2"), -1.0) >= 0:
            self.sp_area_total.setValue(_to_float(st.get("area_total_m2"), self.sp_area_total.value()))
        use_m = bool(st.get("use_manual_wire", False))
        self.chk_use_manual_wire.setChecked(use_m)
        self.chk_project_group.setChecked(bool(st.get("use_project_group", True)))
        if _safe_text(st.get("material")) in ("Cu", "Al"):
            self.cb_material.setCurrentText(_safe_text(st.get("material")))
        if _safe_text(st.get("awg_sel")):
            self.cb_awg.setCurrentText(_safe_text(st.get("awg_sel")))
        self._update_preview()

    def _on_norma_changed(self):
        norma = _safe_text(self.cb_norma.currentText()).strip().upper()
        self.sp_va_m2.setValue(_default_va_m2(norma))
        self._update_preview()

    def _on_area_obj_changed(self):
        name = _safe_text(self.cb_area_obj.currentData()).strip()
        if not name:
            self._update_preview()
            return
        obj = self.doc.getObject(name)
        if obj is None:
            self._update_preview()
            return
        a = _shape_area_m2(obj)
        if _is_wire_like_object(obj) and not _is_closed_object(obj):
            _log_w(f"El objeto '{name}' no esta cerrado; no se puede usar como area de proyecto.")
        if a > 0:
            self.sp_area_total.setValue(a)
        else:
            _log_w(f"El objeto '{name}' no tiene area valida para calculo.")
        self._update_preview()

    def _on_manual_wire_changed(self):
        if _safe_text(self.cb_wire_manual.currentData()).strip():
            self.chk_use_manual_wire.setChecked(True)
        self._update_preview()

    def _update_preview(self):
        sistema = _safe_text(self.cb_system.currentText()).strip()
        poles = _system_poles(sistema)
        v_ll = max(_to_float(self.sp_vll.value(), 0.0), 0.0)
        pf = max(min(_to_float(self.sp_pf.value(), 1.0), 1.0), 0.0)
        growth = max(_to_float(self.sp_growth.value(), 0.0), 0.0)
        demand_method = _safe_text(self.cb_demanda_metodo.currentData()).strip().upper() or "MANUAL"
        area_total_m2 = max(_to_float(self.sp_area_total.value(), 0.0), 0.0)
        va_m2 = max(_to_float(self.sp_va_m2.value(), 0.0), 0.0)
        demanda_manual_va = max(_to_float(self.sp_demanda_va.value(), 0.0), 0.0)
        demanda_area_va = area_total_m2 * va_m2
        if demand_method == "AREA":
            demanda_usada_va = demanda_area_va
        elif demand_method == "MAYOR":
            demanda_usada_va = max(demanda_manual_va, demanda_area_va)
        else:
            demanda_usada_va = demanda_manual_va

        va_per_amp = _va_per_amp(v_ll, poles)
        i_nom = (demanda_usada_va / va_per_amp) if va_per_amp > 0 else 0.0
        i_diseno = i_nom * (1.0 + (growth / 100.0)) * 1.25
        breaker_calc = _next_breaker(i_diseno)
        material = _safe_text(self.cb_material.currentText()).strip() or "Cu"
        awg_sel = _safe_text(self.cb_awg.currentText()).strip() or "12"
        conductor_calc = _awg_for_current(material, max(i_diseno, breaker_calc))

        breaker_sel = _to_int(self.sp_breaker.value(), 0)
        amp_table = _ampacity_table(material)
        amp_sel = _to_float(amp_table.get(awg_sel, 0.0), 0.0)
        va_nom_breaker = breaker_sel * va_per_amp
        va_nom_conductor = amp_sel * va_per_amp

        self.lb_demanda_area.setText(f"{demanda_area_va:.1f} VA ({demanda_area_va / 1000.0:.3f} kVA)")
        self.lb_demanda_usada.setText(f"{demanda_usada_va:.1f} VA ({demanda_usada_va / 1000.0:.3f} kVA)")
        self.lb_i_nom.setText(f"{i_nom:.3f} A")
        self.lb_i_diseno.setText(f"{i_diseno:.3f} A")
        self.lb_breaker_calc.setText(f"{breaker_calc} A")
        self.lb_conductor_calc.setText(_safe_text(conductor_calc))
        self.lb_va_breaker_nom.setText(f"{va_nom_breaker:.1f} VA")
        self.lb_va_conductor_nom.setText(f"{va_nom_conductor:.1f} VA")

    def _apply_system_defaults(self):
        s = _safe_text(self.cb_system.currentText())
        if "120/208" in s:
            self.sp_vln.setValue(120.0)
            self.sp_vll.setValue(208.0)
        elif "277/480" in s:
            self.sp_vln.setValue(277.0)
            self.sp_vll.setValue(480.0)
        else:
            self.sp_vln.setValue(120.0)
            self.sp_vll.setValue(240.0)

    def _obj_by_name(self, name):
        return self.doc.getObject(_safe_text(name).strip())

    def values(self):
        medidor = self._obj_by_name(self.cb_medidor.currentData())
        tablero = self._obj_by_name(self.cb_tablero.currentData())
        demanda_va_manual = _to_float(self.sp_demanda_va.value(), 0.0)
        return {
            "medidor": medidor,
            "tablero": tablero,
            "wire_manual_obj": self._obj_by_name(self.cb_wire_manual.currentData()),
            "area_obj": self._obj_by_name(self.cb_area_obj.currentData()),
            "sistema": _safe_text(self.cb_system.currentText()).strip(),
            "normativa": _safe_text(self.cb_norma.currentText()).strip().upper() or "CR",
            "demand_method": _safe_text(self.cb_demanda_metodo.currentData()).strip().upper() or "MANUAL",
            "carga_base_va_m2": _to_float(self.sp_va_m2.value(), _default_va_m2("CR")),
            "v_ln": _to_float(self.sp_vln.value(), 0.0),
            "v_ll": _to_float(self.sp_vll.value(), 0.0),
            "demanda_va_manual": demanda_va_manual,
            "demanda_kva": demanda_va_manual / 1000.0,
            "pf": _to_float(self.sp_pf.value(), 1.0),
            "growth_pct": _to_float(self.sp_growth.value(), 0.0),
            "breaker_sel": _to_int(self.sp_breaker.value(), 0),
            "material": _safe_text(self.cb_material.currentText()).strip() or "Cu",
            "awg_sel": _safe_text(self.cb_awg.currentText()).strip() or "12",
            "use_manual_wire": bool(self.chk_use_manual_wire.isChecked()),
            "z_route_mm": _to_float(self.sp_zroute.value(), 0.0),
            "area_total_m2": _to_float(self.sp_area_total.value(), 0.0),
            "use_project_group": bool(self.chk_project_group.isChecked()),
            "reuse_wire": bool(self.chk_reuse.isChecked()),
            "notes": _safe_text(self.ed_notes.text()).strip(),
        }


def _find_existing_wire(doc, label):
    for obj in getattr(doc, "Objects", []) or []:
        if _safe_text(getattr(obj, "Label", "")) != label:
            continue
        t = _safe_text(getattr(obj, "TypeId", "")).lower()
        if "wire" in t or "part::part2dobject" in t or hasattr(obj, "Points"):
            return obj
    return None


def _system_poles(system_text):
    s = _safe_text(system_text).upper()
    if s.startswith("3F"):
        return 3
    return 2


def _va_per_amp(v_ll, poles):
    v = max(_to_float(v_ll, 0.0), 0.0)
    p = _to_int(poles, 2)
    if v <= 0:
        return 0.0
    if p >= 3:
        return math.sqrt(3.0) * v
    return v


class _AcometidaTaskPanel:
    def __init__(self, doc):
        self.form = _AcometidaDialog(doc, parent=None)
        self._done = False
        self._result = QtWidgets.QDialog.Rejected
        self._values = {}

    def getStandardButtons(self):
        return int(QtWidgets.QDialogButtonBox.Ok | QtWidgets.QDialogButtonBox.Cancel)

    def accept(self):
        self._values = self.form.values()
        self._result = QtWidgets.QDialog.Accepted
        self._done = True
        return True

    def reject(self):
        self._result = QtWidgets.QDialog.Rejected
        self._done = True
        return True


def _run_task_panel_blocking(panel):
    used_task_panel = False
    try:
        if hasattr(Gui, "Control") and hasattr(Gui.Control, "showDialog"):
            Gui.Control.showDialog(panel)
            used_task_panel = True
        else:
            raise RuntimeError("Gui.Control.showDialog no disponible")
    except Exception as ex:
        _log_w(f"Task Panel no disponible ({ex}); se usa dialogo clasico.")
        dlg = QtWidgets.QDialog()
        dlg.setWindowTitle("Formulario Acometida")
        dlg.setMinimumWidth(700)
        lay = QtWidgets.QVBoxLayout(dlg)
        lay.addWidget(panel.form)
        btns = QtWidgets.QDialogButtonBox(QtWidgets.QDialogButtonBox.Ok | QtWidgets.QDialogButtonBox.Cancel)
        btns.accepted.connect(dlg.accept)
        btns.rejected.connect(dlg.reject)
        lay.addWidget(btns)
        try:
            if QtCore is not None:
                dlg.setWindowModality(QtCore.Qt.NonModal)
            dlg.setModal(False)
        except Exception:
            pass
        dlg.show()
        while dlg.isVisible():
            try:
                QtWidgets.QApplication.processEvents()
                if hasattr(Gui, "updateGui"):
                    Gui.updateGui()
            except Exception:
                pass
            time.sleep(0.02)
        if dlg.result() == QtWidgets.QDialog.Accepted:
            return QtWidgets.QDialog.Accepted, panel.form.values()
        return QtWidgets.QDialog.Rejected, {}

    while used_task_panel and not bool(getattr(panel, "_done", False)):
        try:
            QtWidgets.QApplication.processEvents()
            if hasattr(Gui, "updateGui"):
                Gui.updateGui()
        except Exception:
            pass
        time.sleep(0.02)

    if used_task_panel:
        try:
            Gui.Control.closeDialog()
        except Exception:
            pass
    return getattr(panel, "_result", QtWidgets.QDialog.Rejected), getattr(panel, "_values", {})


def registrar_acometida_y_ruta():
    doc = App.ActiveDocument
    if doc is None:
        doc = App.newDocument("Electrico")

    panel = _AcometidaTaskPanel(doc)
    result, data = _run_task_panel_blocking(panel)
    if result != QtWidgets.QDialog.Accepted:
        _log_i("Operacion cancelada por usuario.")
        return

    medidor = data["medidor"]
    tablero = data["tablero"]
    if medidor is None or tablero is None:
        _log_e("Debe seleccionar medidor y tablero principal.")
        return
    if medidor.Name == tablero.Name:
        _log_e("Medidor y tablero no pueden ser el mismo objeto.")
        return

    sistema = data["sistema"]
    normativa = _safe_text(data.get("normativa", "CR")).strip().upper()
    if normativa not in AREA_LOAD_DEFAULTS:
        normativa = "CR"
    metodo_demanda = _safe_text(data.get("demand_method", "MANUAL")).strip().upper()
    if metodo_demanda not in ("MANUAL", "AREA", "MAYOR"):
        metodo_demanda = "MANUAL"
    carga_base_va_m2 = max(_to_float(data.get("carga_base_va_m2"), _default_va_m2(normativa)), 0.0)
    poles = _system_poles(sistema)
    v_ll = max(_to_float(data["v_ll"], 0.0), 0.001)
    demanda_manual_va = max(_to_float(data.get("demanda_va_manual"), -1.0), 0.0)
    if demanda_manual_va <= 0.0:
        demanda_manual_va = max(_to_float(data.get("demanda_kva"), 0.0), 0.0) * 1000.0
    demanda_manual_kva = demanda_manual_va / 1000.0
    pf = max(min(_to_float(data["pf"], 1.0), 1.0), 0.0)
    growth = max(_to_float(data["growth_pct"], 0.0), 0.0)
    material = data["material"]
    awg_sel = data["awg_sel"]
    breaker_sel = _next_breaker(data["breaker_sel"]) if _to_int(data["breaker_sel"], 0) > 0 else 0
    wire_manual_obj = data.get("wire_manual_obj")
    use_manual_wire = bool(data.get("use_manual_wire")) and (wire_manual_obj is not None)
    area_obj = data.get("area_obj")
    use_project_group = bool(data.get("use_project_group", True))

    source_longitud = "AUTO"
    route_len_m = 0.0
    wire_name_for_row = ""
    wire_manual_name = ""
    area_total_m2 = max(_to_float(data.get("area_total_m2"), 0.0), 0.0)

    if bool(data.get("use_manual_wire")) and wire_manual_obj is None:
        _log_w("Se activo 'usar wire manual' pero no se selecciono wire; se usara ruta automatica.")

    if area_obj is not None and _is_wire_like_object(area_obj) and not _is_closed_object(area_obj):
        _log_w("El objeto de area seleccionado no esta cerrado; se ignora para demanda por area.")

    if area_total_m2 <= 0 and area_obj is not None:
        area_total_m2 = _shape_area_m2(area_obj)

    demanda_area_va = area_total_m2 * carga_base_va_m2
    demanda_area_kva = demanda_area_va / 1000.0
    if metodo_demanda == "AREA":
        demanda_usada_va = demanda_area_va
    elif metodo_demanda == "MAYOR":
        demanda_usada_va = max(demanda_manual_va, demanda_area_va)
    else:
        demanda_usada_va = demanda_manual_va
    demanda_usada_kva = demanda_usada_va / 1000.0

    if metodo_demanda in ("AREA", "MAYOR") and area_total_m2 <= 0:
        _log_w("Area total del proyecto es 0.0 m2; la demanda por area resulta 0.0 kVA.")

    project_group = None
    if use_project_group:
        project_group = _ensure_group(doc, "Proyecto_Acometida")
        _add_to_group_safe(project_group, medidor)
        _add_to_group_safe(project_group, tablero)
        _add_to_group_safe(project_group, wire_manual_obj)
        _add_to_group_safe(project_group, area_obj)

    p0 = _connection_point(medidor)
    p1 = _connection_point(tablero)
    points = _route_points_ortho(p0, p1, data["z_route_mm"])
    route_len_mm_auto = _path_length_mm(points)
    route_len_m_auto = route_len_mm_auto / 1000.0

    if use_manual_wire:
        wire_manual_name = _safe_text(getattr(wire_manual_obj, "Name", ""))
        route_len_mm_manual = _shape_length_mm(wire_manual_obj)
        if route_len_mm_manual > 0:
            route_len_m = route_len_mm_manual / 1000.0
            source_longitud = "MANUAL"
            wire_name_for_row = wire_manual_name
        else:
            _log_w("Wire manual sin longitud valida; se usara ruta automatica.")
            use_manual_wire = False
            route_len_m = route_len_m_auto
            source_longitud = "AUTO"
    else:
        route_len_m = route_len_m_auto
        source_longitud = "AUTO"

    p_kw = demanda_usada_kva * pf
    va_per_amp = _va_per_amp(v_ll, poles)
    i_nom = (demanda_usada_va / va_per_amp) if va_per_amp > 0 else 0.0

    i_diseno = i_nom * (1.0 + (growth / 100.0)) * 1.25
    breaker_calc = _next_breaker(i_diseno)
    conductor_calc = _awg_for_current(material, max(i_diseno, breaker_calc))

    if breaker_sel <= 0:
        breaker_sel = _next_breaker(i_diseno)
    if not awg_sel:
        awg_sel = _awg_for_current(material, breaker_sel)

    caida_sel = _voltage_drop_pct(route_len_m, i_diseno, v_ll, poles, awg_sel)
    caida_calc = _voltage_drop_pct(route_len_m, i_diseno, v_ll, poles, conductor_calc)

    wire_obj = None
    if not use_manual_wire:
        wire_label = "Acometida_{}_{}".format(
            _safe_name(getattr(medidor, "Label", medidor.Name)),
            _safe_name(getattr(tablero, "Label", tablero.Name)),
        )

        if data["reuse_wire"]:
            old = _find_existing_wire(doc, wire_label)
            if old is not None:
                try:
                    doc.removeObject(old.Name)
                    _log_i(f"Wire anterior reemplazado: {wire_label}")
                except Exception as ex:
                    _log_w(f"No se pudo remover wire previo: {ex}")

        wire_obj = _make_wire(points)
        wire_obj.Label = wire_label
        wire_name_for_row = _safe_text(getattr(wire_obj, "Name", ""))
        try:
            if hasattr(wire_obj, "FilletRadius"):
                wire_obj.FilletRadius = 0.0
        except Exception:
            pass
        try:
            vo = getattr(wire_obj, "ViewObject", None)
            if vo is not None:
                if hasattr(vo, "LineWidth"):
                    vo.LineWidth = 3.0
                if hasattr(vo, "LineColor"):
                    vo.LineColor = (0.85, 0.35, 0.1)
        except Exception:
            pass

        g_con = _ensure_group(doc, "Conexiones")
        try:
            _add_to_group_safe(g_con, wire_obj)
        except Exception as ex:
            _log_w(f"No se pudo mover wire al grupo Conexiones: {ex}")
        _add_to_group_safe(project_group, wire_obj)

    sheet, used_cols = _ensure_sheet(doc, "Acometida")
    row = _first_empty_row(sheet, used_cols, start_row=2)

    timestamp = datetime.now().strftime("%Y-%m-%d %H:%M:%S")
    values = [
        timestamp,
        _safe_text(getattr(medidor, "Label", medidor.Name)),
        _safe_text(getattr(tablero, "Label", tablero.Name)),
        sistema,
        normativa,
        metodo_demanda,
        carga_base_va_m2,
        area_total_m2,
        demanda_manual_kva,
        demanda_area_kva,
        demanda_usada_kva,
        poles,
        data["v_ln"],
        v_ll,
        pf,
        p_kw,
        i_nom,
        growth,
        i_diseno,
        material,
        breaker_sel,
        breaker_calc,
        awg_sel,
        conductor_calc,
        route_len_m,
        caida_sel,
        caida_calc,
        wire_name_for_row,
        data["notes"],
        source_longitud,
        wire_manual_name,
    ]

    _save_state(
        {
            "medidor_name": _safe_text(getattr(medidor, "Name", "")),
            "tablero_name": _safe_text(getattr(tablero, "Name", "")),
            "wire_manual_name": _safe_text(getattr(wire_manual_obj, "Name", "")),
            "area_obj_name": _safe_text(getattr(area_obj, "Name", "")),
            "sistema": sistema,
            "normativa": normativa,
            "demand_method": metodo_demanda,
            "carga_base_va_m2": carga_base_va_m2,
            "demanda_va_manual": demanda_manual_va,
            "demanda_kva": demanda_manual_kva,
            "pf": pf,
            "growth_pct": growth,
            "breaker_sel": breaker_sel,
            "material": material,
            "awg_sel": awg_sel,
            "z_route_mm": _to_float(data.get("z_route_mm"), 0.0),
            "use_manual_wire": use_manual_wire,
            "use_project_group": use_project_group,
            "area_total_m2": area_total_m2,
        }
    )

    for i, value in enumerate(values, start=1):
        cell = f"{_col_letter(i)}{row}"
        if isinstance(value, (int, float)):
            dec = 0 if i in (12, 21, 22) else 3
            _set_number(sheet, cell, value, decimals=dec)
        else:
            _set_text(sheet, cell, value)

    try:
        sheet.recompute()
        doc.recompute()
    except Exception as ex:
        _log_w(f"Recompute con advertencia: {ex}")

    _log_i(
        "Acometida registrada. Norma={}, Metodo={}, DemManual={:.1f} VA, DemArea={:.1f} VA, "
        "DemUsada={:.1f} VA, FuenteRuta={}, GrupoProyecto={}, I_nom={:.3f} A, I_diseno={:.3f} A, "
        "Breaker_calc={} A, Conductor_calc={}, Ruta={:.3f} m, Caida_sel={:.3f}%, Area={:.3f} m2".format(
            normativa, metodo_demanda, demanda_manual_va, demanda_area_va, demanda_usada_va,
            source_longitud, "SI" if use_project_group else "NO",
            i_nom, i_diseno, breaker_calc, conductor_calc, route_len_m, caida_sel, area_total_m2
        )
    )


if __name__ == "__main__":
    registrar_acometida_y_ruta()

# -*- coding: utf-8 -*-
# MenuText: Analizar areas rectangulares desde muros BIM
# ToolTip: Seleccione uno o varios muros BIM y cree el analisis rectangular de areas.
# Toolbar: Areas
# Transaction: self
# Revision: 2026-08-11 20:22 America/Costa_Rica
# FreeCAD: 1.1.3

"""ElectricCR entry point for the rectangular BIM-wall area analysis."""

from __future__ import annotations

import importlib.util
import os

import FreeCAD as App
import FreeCADGui as Gui


PREFIX = "[ElectricCR][AREAS RECTANGULARES] "


def _load_engine():
    macro_dir = os.path.dirname(os.path.abspath(__file__))
    engine_path = os.path.join(
        os.path.dirname(macro_dir),
        "FacilArquitecturaWB",
        "core",
        "rectangular_area_analysis.py",
    )
    if not os.path.isfile(engine_path):
        raise RuntimeError(
            "No se encontro el motor interno FacilArquitecturaWB/core/"
            "rectangular_area_analysis.py. Verifique la instalacion del repositorio."
        )
    module_name = "facilarq_rectangular_area_analysis_runtime"
    spec = importlib.util.spec_from_file_location(module_name, engine_path)
    if spec is None or spec.loader is None:
        raise RuntimeError("No fue posible preparar el motor de areas rectangulares.")
    module = importlib.util.module_from_spec(spec)
    spec.loader.exec_module(module)
    App.Console.PrintMessage(PREFIX + "Motor cargado desde: " + engine_path + "\n")
    return module


def main():
    doc = App.ActiveDocument
    if doc is None:
        raise RuntimeError("Abra un documento antes de ejecutar la macro.")

    engine = _load_engine()
    selected = list(Gui.Selection.getSelection() or [])
    if not selected:
        raise RuntimeError("Seleccione uno o varios muros BIM.")

    walls = [obj for obj in selected if engine.is_bim_wall(obj)]
    if len(walls) != len(selected):
        invalid = [
            str(getattr(obj, "Label", getattr(obj, "Name", "?")) or "?")
            for obj in selected
            if obj not in walls
        ]
        raise RuntimeError(
            "La seleccion contiene objetos que no son muros BIM validos: %s"
            % ", ".join(invalid)
        )

    unusable = [
        str(getattr(wall, "Label", getattr(wall, "Name", "?")) or "?")
        for wall in walls
        if engine.wall_centerline(wall) is None
    ]
    if unusable:
        raise RuntimeError("Muros sin eje/base utilizable: %s" % ", ".join(unusable))

    App.Console.PrintMessage(
        PREFIX + "Muros BIM seleccionados: %s\n"
        % ", ".join(str(getattr(wall, "Name", "?")) for wall in walls)
    )
    return engine.generate_rectangular_areas(doc=doc, walls=walls)


try:
    ELECTRICCR_RECTANGULAR_AREAS_RESULT = main()
except Exception as exc:
    App.Console.PrintError(PREFIX + "Error: %s\n" % exc)
    raise

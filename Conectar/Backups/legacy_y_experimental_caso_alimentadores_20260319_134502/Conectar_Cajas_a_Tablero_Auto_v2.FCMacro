# -*- coding: utf-8 -*-
# MenuText: [EXPERIMENTAL] Conectar Alimentadores a Tablero v2
# Icon: Conectar_Alimentadores_a_Tablero_Auto_v2.svg
"""
Macro: Conectar_Alimentadores_a_Tablero_Auto_v2
Description:
Automatic feeder routing from octagonal boxes to electrical panels using guide routes.

This version reorganizes the original macro with a cleaner architecture.

Date:
2026

Author:
Codex

Notes:
Uses channel routing concept and guide routes.
Does not attempt full building autorouting.
Uses optional NetworkX only for logical path computation.
Keeps geometry creation inside FreeCAD.
"""

import math
import re
from collections import defaultdict

import FreeCAD as App
import Draft

try:
    import FreeCADGui as Gui
except Exception:
    Gui = None

try:
    from PySide2 import QtWidgets, QtCore
except Exception:
    try:
        from PySide import QtGui as QtWidgets  # type: ignore
        from PySide import QtCore  # type: ignore
    except Exception:
        QtWidgets = None
        QtCore = None

try:
    import Part
except Exception:
    Part = None

try:
    import DraftGeomUtils
except Exception:
    DraftGeomUtils = None

try:
    import networkx as nx
    NETWORKX_AVAILABLE = True
except Exception:
    nx = None
    NETWORKX_AVAILABLE = False


TAG = "[CAJA_TAB_V2]"
DEFAULT_CONDUIT = "EMT"
DEFAULT_DIAMETER = 22.2
DEFAULT_ROUTE_Z = 3000.0
DEFAULT_BEND_RADIUS = 100.0
DEFAULT_CIRCUIT_SEPARATION = 50.0
DEFAULT_PANEL_TITLE = "[EXPERIMENTAL] Conectar Alimentadores a Tablero v2"
EPS = 1e-6
CARAS_TABLERO_ACTIVAS = []


def log_info(msg):
    App.Console.PrintMessage(f"{TAG} {msg}\n")


def log_error(msg):
    App.Console.PrintError(f"{TAG} {msg}\n")


def texto_seguro(value):
    try:
        return str(value or "")
    except Exception:
        return ""


def vec(x=0.0, y=0.0, z=0.0):
    return App.Vector(float(x), float(y), float(z))


def dist_xy(a, b):
    dx = float(a.x) - float(b.x)
    dy = float(a.y) - float(b.y)
    return (dx * dx + dy * dy) ** 0.5


def dedup_points(points):
    out = []
    for p in (points or []):
        if not out:
            out.append(vec(p.x, p.y, p.z))
            continue
        if out[-1].distanceToPoint(p) > 0.1:
            out.append(vec(p.x, p.y, p.z))
    return out


def natural_key(text):
    s = texto_seguro(text)
    return [int(t) if t.isdigit() else t.lower() for t in re.split(r"([0-9]+)", s)]


def es_grupo(obj):
    if obj is None:
        return False
    type_id = texto_seguro(getattr(obj, "TypeId", ""))
    if type_id.startswith("App::DocumentObjectGroup"):
        return True
    return hasattr(obj, "Group")


def iterar_padres(obj, visitados=None):
    if obj is None:
        return
    if visitados is None:
        visitados = set()
    for parent in list(getattr(obj, "InList", []) or []):
        pname = texto_seguro(getattr(parent, "Name", ""))
        if pname and pname in visitados:
            continue
        if pname:
            visitados.add(pname)
        yield parent
        for pp in iterar_padres(parent, visitados):
            yield pp


def es_tablero(obj):
    if obj is None or es_grupo(obj):
        return False
    tipo = texto_seguro(getattr(obj, "Tipo", "")).strip().lower()
    if "tablero" in tipo:
        return True
    txt = f"{texto_seguro(getattr(obj, 'Label', ''))} {texto_seguro(getattr(obj, 'Name', ''))}".lower()
    return "tablero" in txt


def es_octogonal(obj):
    if obj is None or es_grupo(obj):
        return False
    tipo = texto_seguro(getattr(obj, "Tipo", "")).strip()
    if tipo == "EMT_Octagon_Box":
        return True
    txt = f"{texto_seguro(getattr(obj, 'Label', ''))} {texto_seguro(getattr(obj, 'Name', ''))}".lower()
    if "caja emt octogonal" in txt or "emt_octagon_box" in txt:
        return True
    if hasattr(obj, "CajaOrigenKey") and hasattr(obj, "PuertosJSON"):
        return True
    return False


def es_octogonal_usable(obj):
    if not es_octogonal(obj):
        return False
    txt = f"{texto_seguro(getattr(obj, 'Label', ''))} {texto_seguro(getattr(obj, 'Name', ''))}".strip().lower()
    if not txt:
        return False
    skip_tokens = (
        "master",
        "template",
        "plantilla",
        "prototype",
        "prototipo",
    )
    if any(tok in txt for tok in skip_tokens):
        return False
    return True


def es_grupo_tecnico(texto):
    low = texto_seguro(texto).strip().lower()
    if not low:
        return True
    tokens = (
        "cajas_",
        "tuberias_",
        "conexiones",
        "electrico",
        "tomacorrientes",
        "apagadores",
        "dispositivos",
        "boxes",
        "conduit",
    )
    return any(tok in low for tok in tokens)


def circuito_id_valido(texto):
    txt = texto_seguro(texto).strip()
    low = txt.lower()
    if not txt:
        return False
    invalid_tokens = (
        "caja emt octogonal",
        "master",
        "sin_circuito",
        "sincircuito",
        "sin circuito",
    )
    if any(tok in low for tok in invalid_tokens):
        return False
    return True


def obtener_centro_objeto(obj):
    if obj is None:
        return vec(0.0, 0.0, 0.0)
    try:
        shape = getattr(obj, "Shape", None)
        if shape is not None and not shape.isNull():
            bb = shape.BoundBox
            return vec(0.5 * (bb.XMin + bb.XMax), 0.5 * (bb.YMin + bb.YMax), 0.5 * (bb.ZMin + bb.ZMax))
    except Exception:
        pass
    try:
        return obj.Placement.Base
    except Exception:
        return vec(0.0, 0.0, 0.0)


def obtener_bbox(obj):
    try:
        shape = getattr(obj, "Shape", None)
        if shape is not None and not shape.isNull():
            return shape.BoundBox
    except Exception:
        pass
    return None


def obtener_puntos_polilinea(obj):
    if obj is None or es_grupo(obj):
        return []
    try:
        shape = getattr(obj, "Shape", None)
    except Exception:
        shape = None
    if shape is None:
        return []
    try:
        if shape.isNull():
            return []
    except Exception:
        pass

    candidatos = []
    try:
        for wire in list(getattr(shape, "Wires", []) or []):
            pts = []
            for vtx in list(getattr(wire, "OrderedVertexes", []) or []):
                pt = getattr(vtx, "Point", None)
                if pt is not None:
                    pts.append(vec(pt.x, pt.y, pt.z))
            if len(pts) >= 2:
                candidatos.append(dedup_points(pts))
    except Exception:
        pass

    if candidatos:
        candidatos.sort(key=lambda pts: len(pts), reverse=True)
        return candidatos[0]

    try:
        pts = []
        for vtx in list(getattr(shape, "OrderedVertexes", []) or []):
            pt = getattr(vtx, "Point", None)
            if pt is not None:
                pts.append(vec(pt.x, pt.y, pt.z))
        if len(pts) >= 2:
            return dedup_points(pts)
    except Exception:
        pass
    return []


def longitud_segmento_xy(a, b):
    dx = float(b.x) - float(a.x)
    dy = float(b.y) - float(a.y)
    return (dx * dx + dy * dy) ** 0.5


def radio_curva_efectivo(points, radio_solicitado):
    pts = dedup_points(points)
    if len(pts) < 3:
        return 0.0
    minimo = None
    for a, b in zip(pts[:-1], pts[1:]):
        seg_len = float(a.distanceToPoint(b))
        if seg_len <= 0.1:
            continue
        if minimo is None or seg_len < minimo:
            minimo = seg_len
    if minimo is None:
        return 0.0
    radio_max = max(0.0, float(minimo) * 0.45)
    return min(float(radio_solicitado), radio_max)


def es_ruta_guia(obj):
    pts = obtener_puntos_polilinea(obj)
    if len(pts) < 2:
        return False
    try:
        if pts[0].distanceToPoint(pts[-1]) <= 0.1:
            return False
    except Exception:
        pass
    return True


def resolver_grupo_circuito(obj):
    for parent in iterar_padres(obj):
        txt = texto_seguro(getattr(parent, "Label", "")) or texto_seguro(getattr(parent, "Name", ""))
        low = txt.lower()
        if es_grupo(parent) and not es_grupo_tecnico(txt):
            if low.startswith("tp-") or "circuito" in low:
                return parent
    for parent in iterar_padres(obj):
        txt = texto_seguro(getattr(parent, "Label", "")) or texto_seguro(getattr(parent, "Name", ""))
        if es_grupo(parent) and not es_grupo_tecnico(txt):
            return parent
    return None


def obtener_circuito_desde_objeto(obj):
    grupo = resolver_grupo_circuito(obj)
    if grupo is not None:
        return texto_seguro(getattr(grupo, "Label", "")) or texto_seguro(getattr(grupo, "Name", ""))
    cid = texto_seguro(getattr(obj, "CircuitoID", "")).strip()
    if circuito_id_valido(cid):
        return cid
    txt = texto_seguro(getattr(obj, "Label", "")) or texto_seguro(getattr(obj, "Name", ""))
    if circuito_id_valido(txt) and ("circuito" in txt.lower()):
        return txt
    return ""


def obtener_grupo_circuito(obj):
    return resolver_grupo_circuito(obj)


def asegurar_subgrupo(doc, parent, label):
    if parent is None:
        return None
    for child in list(getattr(parent, "Group", []) or []):
        if texto_seguro(getattr(child, "Label", "")) == label or texto_seguro(getattr(child, "Name", "")) == label:
            return child
    obj = doc.addObject("App::DocumentObjectGroup", re.sub(r"[^0-9A-Za-z_]+", "_", label))
    obj.Label = label
    try:
        parent.addObject(obj)
    except Exception:
        pass
    return obj


def asegurar_objeto_en_grupo(group_obj, obj):
    if group_obj is None or obj is None:
        return
    try:
        if obj not in list(group_obj.Group or []):
            group_obj.addObject(obj)
    except Exception:
        pass


def limpiar_alimentadores_v2(doc, group_obj):
    if group_obj is None:
        return 0
    eliminados = 0
    for child in list(getattr(group_obj, "Group", []) or []):
        try:
            if texto_seguro(getattr(child, "GeneradoPor", "")) == "Conectar_Cajas_a_Tablero_Auto_v2":
                name = child.Name
                try:
                    group_obj.removeObject(child)
                except Exception:
                    pass
                doc.removeObject(name)
                eliminados += 1
        except Exception:
            pass
    return eliminados


def clasificar_cara_desde_face(face):
    if face is None:
        return None
    normal = None
    try:
        u0, u1, v0, v1 = face.ParameterRange
        normal = face.normalAt(0.5 * (u0 + u1), 0.5 * (v0 + v1))
    except Exception:
        try:
            normal = face.normalAt(0.0, 0.0)
        except Exception:
            normal = None
    if normal is None:
        return None
    ax = abs(float(normal.x))
    ay = abs(float(normal.y))
    az = abs(float(normal.z))
    if az >= ax and az >= ay:
        return "Top" if float(normal.z) >= 0.0 else "Bottom"
    if ax >= ay:
        return "East" if float(normal.x) >= 0.0 else "West"
    return "North" if float(normal.y) >= 0.0 else "South"


def punto_panel_en_cara(tablero, cara, referencia):
    bb = obtener_bbox(tablero)
    if bb is None:
        return obtener_centro_objeto(tablero)
    ref = referencia if referencia is not None else obtener_centro_objeto(tablero)
    x = min(max(float(ref.x), float(bb.XMin)), float(bb.XMax))
    y = min(max(float(ref.y), float(bb.YMin)), float(bb.YMax))
    z = min(max(float(ref.z), float(bb.ZMin)), float(bb.ZMax))
    cara_txt = texto_seguro(cara).strip()
    if cara_txt == "Top":
        return vec(x, y, bb.ZMax)
    if cara_txt == "Bottom":
        return vec(x, y, bb.ZMin)
    if cara_txt == "East":
        return vec(bb.XMax, y, z)
    if cara_txt == "West":
        return vec(bb.XMin, y, z)
    if cara_txt == "North":
        return vec(x, bb.YMax, z)
    if cara_txt == "South":
        return vec(x, bb.YMin, z)
    return obtener_centro_objeto(tablero)


def punto_panel_mas_cercano(tablero, caras_activas, referencia):
    caras = list(caras_activas or [])
    if not caras:
        caras = ["East", "West", "North", "South", "Top", "Bottom"]
    mejor = None
    mejor_d = None
    ref = referencia if referencia is not None else obtener_centro_objeto(tablero)
    for cara in caras:
        pt = punto_panel_en_cara(tablero, cara, ref)
        d = ref.distanceToPoint(pt)
        if mejor is None or d < mejor_d:
            mejor = {"cara": cara, "punto": pt}
            mejor_d = d
    return mejor


def clasificar_ruta_borde_tablero_top(tablero, ruta):
    centro = obtener_centro_objeto(tablero)
    pts = obtener_puntos_polilinea(ruta)
    proj = project_point_to_polyline_xy(centro, pts)
    if proj is None:
        p = obtener_centro_objeto(ruta)
    else:
        p = proj["point"]
    dx = float(p.x) - float(centro.x)
    dy = float(p.y) - float(centro.y)
    if abs(dx) >= abs(dy):
        borde = "West" if dx <= 0.0 else "East"
    else:
        borde = "South" if dy <= 0.0 else "North"
    return borde, vec(p.x, p.y, centro.z)


def project_point_to_segment_xy(p, a, b):
    abx = float(b.x) - float(a.x)
    aby = float(b.y) - float(a.y)
    den = (abx * abx) + (aby * aby)
    if den <= EPS:
        proj = vec(a.x, a.y, 0.0)
        return proj, 0.0, dist_xy(p, proj)
    apx = float(p.x) - float(a.x)
    apy = float(p.y) - float(a.y)
    t = ((apx * abx) + (apy * aby)) / den
    t = max(0.0, min(1.0, t))
    proj = vec(float(a.x) + (abx * t), float(a.y) + (aby * t), 0.0)
    return proj, t, dist_xy(p, proj)


def project_point_to_polyline_xy(p, pts):
    if len(pts or []) < 2:
        return None
    best = None
    acc = 0.0
    for idx, (a, b) in enumerate(zip(pts[:-1], pts[1:])):
        seg_len = dist_xy(a, b)
        proj, t, dist = project_point_to_segment_xy(p, a, b)
        s = acc + (seg_len * float(t))
        item = {
            "index": idx,
            "point": proj,
            "distance": float(dist),
            "s": float(s),
        }
        if best is None or item["distance"] < best["distance"]:
            best = item
        acc += seg_len
    return best


def guide_path_between(pts, proj_a, proj_b, z_level):
    if proj_a is None or proj_b is None:
        return []
    pa = vec(proj_a["point"].x, proj_a["point"].y, z_level)
    pb = vec(proj_b["point"].x, proj_b["point"].y, z_level)
    if int(proj_a["index"]) == int(proj_b["index"]):
        return dedup_points([pa, pb])

    out = [pa]
    if float(proj_a["s"]) <= float(proj_b["s"]):
        for idx in range(int(proj_a["index"]) + 1, int(proj_b["index"]) + 1):
            vtx = pts[idx]
            out.append(vec(vtx.x, vtx.y, z_level))
    else:
        for idx in range(int(proj_a["index"]), int(proj_b["index"]), -1):
            vtx = pts[idx]
            out.append(vec(vtx.x, vtx.y, z_level))
    out.append(pb)
    return dedup_points(out)


def is_guide_node_kind(kind):
    return texto_seguro(kind).strip() in ("guide_vertex", "guide_projection")


def add_graph_node(graph, key, point, kind):
    if graph is None:
        return
    graph.add_node(key, point=vec(point.x, point.y, point.z), kind=texto_seguro(kind))


def add_graph_edge(graph, key_a, key_b):
    if graph is None or key_a == key_b:
        return
    try:
        p1 = graph.nodes[key_a]["point"]
        p2 = graph.nodes[key_b]["point"]
    except Exception:
        return
    weight = float(p1.distanceToPoint(p2))
    graph.add_edge(key_a, key_b, weight=weight)


def construir_grafo_ruteo_feeders_networkx(p_caja_ruta, pts_guia, p_panel_ruta):
    if not NETWORKX_AVAILABLE:
        return None
    if len(pts_guia or []) < 2:
        return None

    proj_caja = project_point_to_polyline_xy(p_caja_ruta, pts_guia)
    proj_panel = project_point_to_polyline_xy(p_panel_ruta, pts_guia)
    if proj_caja is None or proj_panel is None:
        return None

    graph = nx.Graph()
    add_graph_node(graph, "box", p_caja_ruta, "box")
    add_graph_node(graph, "panel", p_panel_ruta, "panel")
    add_graph_node(graph, "proj_box", vec(proj_caja["point"].x, proj_caja["point"].y, p_caja_ruta.z), "guide_projection")
    add_graph_node(graph, "proj_panel", vec(proj_panel["point"].x, proj_panel["point"].y, p_panel_ruta.z), "guide_projection")

    for idx, pt in enumerate(pts_guia):
        add_graph_node(graph, f"g{idx}", vec(pt.x, pt.y, p_caja_ruta.z), "guide_vertex")

    for idx in range(len(pts_guia) - 1):
        add_graph_edge(graph, f"g{idx}", f"g{idx + 1}")

    add_graph_edge(graph, "box", "proj_box")
    add_graph_edge(graph, "panel", "proj_panel")

    idx_box = int(proj_caja["index"])
    idx_panel = int(proj_panel["index"])
    add_graph_edge(graph, "proj_box", f"g{idx_box}")
    add_graph_edge(graph, "proj_box", f"g{idx_box + 1}")
    add_graph_edge(graph, "proj_panel", f"g{idx_panel}")
    add_graph_edge(graph, "proj_panel", f"g{idx_panel + 1}")

    if idx_box == idx_panel:
        add_graph_edge(graph, "proj_box", "proj_panel")

    log_info(
        "NetworkX grafo construido | nodos={} | aristas={}".format(
            graph.number_of_nodes(),
            graph.number_of_edges(),
        )
    )
    return graph


def ruta_logica_networkx(p_caja_ruta, pts_guia, p_panel_ruta, route_z):
    graph = construir_grafo_ruteo_feeders_networkx(p_caja_ruta, pts_guia, p_panel_ruta)
    if graph is None:
        return None
    try:
        path_keys = nx.shortest_path(graph, "box", "panel", weight="weight")
    except Exception as ex:
        log_error(f"NetworkX shortest_path fallo: {ex}")
        return None

    out = []
    for idx, key in enumerate(path_keys):
        node = graph.nodes[key]
        pt = node["point"]
        kind = texto_seguro(node.get("kind", ""))
        current = vec(pt.x, pt.y, route_z)
        if idx == 0:
            out.append(current)
            continue

        prev_node = graph.nodes[path_keys[idx - 1]]
        prev_pt = prev_node["point"]
        prev_kind = texto_seguro(prev_node.get("kind", ""))
        prev_current = vec(prev_pt.x, prev_pt.y, route_z)

        if (prev_kind == "box" and is_guide_node_kind(kind)) or (is_guide_node_kind(prev_kind) and kind == "panel") or (prev_kind == "box" and kind == "panel"):
            seg = ruta_ortogonal_xy(prev_current, current, route_z)
            out.extend(seg[1:])
        else:
            out.append(current)

    out = dedup_points(out)
    log_info(
        "NetworkX ruta calculada | nodos_camino={} | puntos={}".format(
            len(path_keys),
            len(out),
        )
    )
    return out


def ordenar_items_para_canal(items):
    if not items:
        return []
    enriched = []
    for item in list(items or []):
        caja = item.get("caja")
        ruta = item.get("ruta")
        pts = obtener_puntos_polilinea(ruta)
        proj = project_point_to_polyline_xy(obtener_centro_objeto(caja), pts)
        sval = float(proj["s"]) if proj is not None else 0.0
        enriched.append((sval, natural_key(item.get("circuito", "")), item))
    enriched.sort(key=lambda row: (row[0], row[1]))
    return [row[2] for row in enriched]


def valores_repartidos(count, vmin, vmax):
    if count <= 1:
        return [0.5 * (float(vmin) + float(vmax))]
    step = (float(vmax) - float(vmin)) / float(max(1, count - 1))
    return [float(vmin) + (step * i) for i in range(count)]


def construir_slots_panel_top(tablero, items_por_ruta, cfg):
    bb = obtener_bbox(tablero)
    if bb is None:
        return {}

    separation = max(10.0, float(cfg.get("separation", DEFAULT_CIRCUIT_SEPARATION)))
    z_top = float(bb.ZMax)
    x_margin = max(separation, 35.0)
    y_margin = max(separation, 35.0)
    x_left = float(bb.XMin) + x_margin
    x_right = float(bb.XMax) - x_margin
    y_bottom = float(bb.YMin) + y_margin
    y_top = float(bb.YMax) - y_margin

    rutas_info = []
    for ruta_name, items in items_por_ruta.items():
        if not items:
            continue
        ruta = items[0].get("ruta")
        borde, anchor = clasificar_ruta_borde_tablero_top(tablero, ruta)
        rutas_info.append({
            "ruta_name": ruta_name,
            "ruta": ruta,
            "borde": borde,
            "anchor": anchor,
            "items": ordenar_items_para_canal(items),
        })

    bordes_orden = {
        "West": [],
        "North": [],
        "East": [],
        "South": [],
    }
    for info in rutas_info:
        bordes_orden[info["borde"]].append(info)

    bordes_orden["West"].sort(key=lambda info: float(info["anchor"].y), reverse=True)
    bordes_orden["East"].sort(key=lambda info: float(info["anchor"].y), reverse=True)
    bordes_orden["North"].sort(key=lambda info: float(info["anchor"].x))
    bordes_orden["South"].sort(key=lambda info: float(info["anchor"].x))

    out = {}
    for borde, grupos in bordes_orden.items():
        if not grupos:
            continue
        if borde in ("West", "East"):
            block_values = valores_repartidos(len(grupos), y_bottom, y_top)
            available_block = max(separation, (y_top - y_bottom) / float(max(1, len(grupos))))
            for group_index, info in enumerate(grupos):
                y0 = block_values[group_index]
                items = info["items"]
                if not items:
                    continue
                row_gap = min(separation * 0.9, 80.0)
                span = min(max(0.0, available_block - separation), max(0.0, (len(items) - 1) * separation))
                y_values = valores_repartidos(len(items), y0 - (0.5 * span), y0 + (0.5 * span))
                for idx, item in enumerate(items):
                    x = float(bb.XMin) + ((idx % 2) * row_gap) if borde == "West" else float(bb.XMax) - ((idx % 2) * row_gap)
                    y = y_values[idx]
                    y = min(max(y, y_bottom), y_top)
                    out[texto_seguro(getattr(item["caja"], "Name", ""))] = {
                        "cara": "Top",
                        "punto": vec(x, y, z_top),
                        "borde": borde,
                        "slot": idx,
                    }
        else:
            block_values = valores_repartidos(len(grupos), x_left, x_right)
            available_block = max(separation, (x_right - x_left) / float(max(1, len(grupos))))
            for group_index, info in enumerate(grupos):
                x0 = block_values[group_index]
                items = info["items"]
                if not items:
                    continue
                row_gap = min(separation * 0.9, 80.0)
                span = min(max(0.0, available_block - separation), max(0.0, (len(items) - 1) * separation))
                x_values = valores_repartidos(len(items), x0 - (0.5 * span), x0 + (0.5 * span))
                for idx, item in enumerate(items):
                    y = float(bb.YMax) - ((idx % 2) * row_gap) if borde == "North" else float(bb.YMin) + ((idx % 2) * row_gap)
                    x = x_values[idx]
                    x = min(max(x, x_left), x_right)
                    out[texto_seguro(getattr(item["caja"], "Name", ""))] = {
                        "cara": "Top",
                        "punto": vec(x, y, z_top),
                        "borde": borde,
                        "slot": idx,
                    }

    for ruta_name, items in items_por_ruta.items():
        for item in items:
            key = texto_seguro(getattr(item["caja"], "Name", ""))
            if key in out:
                continue
            out[key] = punto_panel_mas_cercano(tablero, ["Top"], obtener_centro_objeto(item["caja"]))

    for info in rutas_info:
        log_info(
            "Canal tablero | ruta={} | borde={} | circuitos={}".format(
                texto_seguro(getattr(info["ruta"], "Label", "")) or texto_seguro(getattr(info["ruta"], "Name", "")),
                info["borde"],
                len(info["items"]),
            )
        )
    return out


def ruta_ortogonal_xy(a, b, z_level):
    p1 = vec(a.x, a.y, z_level)
    p2 = vec(b.x, b.y, z_level)
    if abs(float(p1.x) - float(p2.x)) <= 0.1 or abs(float(p1.y) - float(p2.y)) <= 0.1:
        return dedup_points([p1, p2])
    dx = abs(float(p2.x) - float(p1.x))
    dy = abs(float(p2.y) - float(p1.y))
    if dx >= dy:
        mid = vec(p2.x, p1.y, z_level)
    else:
        mid = vec(p1.x, p2.y, z_level)
    return dedup_points([p1, mid, p2])


def part_wire_from_points(points):
    if Part is None:
        return None
    pts = dedup_points(points)
    if len(pts) < 2:
        return None
    try:
        poly = Part.makePolygon(pts)
        return Part.Wire(poly.Edges)
    except Exception:
        return None


def points_from_wire(wire, z_override=None):
    if wire is None or Part is None:
        return []
    cur = wire
    try:
        wires = list(getattr(cur, "Wires", []) or [])
        if wires:
            cur = wires[0]
    except Exception:
        pass
    edges = list(getattr(cur, "Edges", []) or [])
    if not edges:
        return []
    try:
        edges = Part.__sortEdges__(edges)
    except Exception:
        pass
    pts = []
    for edge in edges:
        verts = list(getattr(edge, "Vertexes", []) or [])
        if len(verts) >= 1:
            p0 = verts[0].Point
            z0 = float(z_override) if z_override is not None else float(p0.z)
            pts.append(vec(p0.x, p0.y, z0))
        if len(verts) >= 2:
            p1 = verts[-1].Point
            z1 = float(z_override) if z_override is not None else float(p1.z)
            pts.append(vec(p1.x, p1.y, z1))
    return dedup_points(pts)


def offset_vector_for_points(points, offset_mm):
    pts = dedup_points(points)
    d = float(offset_mm)
    for a, b in zip(pts[:-1], pts[1:]):
        dx = float(b.x) - float(a.x)
        dy = float(b.y) - float(a.y)
        seg_len = (dx * dx + dy * dy) ** 0.5
        if seg_len > EPS:
            return vec((-dy / seg_len) * d, (dx / seg_len) * d, 0.0)
    return vec(0.0, 0.0, 0.0)


def make_draft_wire(points):
    maker = getattr(Draft, "makeWire", None)
    if maker is None:
        maker = getattr(Draft, "make_wire", None)
    if maker is None:
        raise RuntimeError("No se encontro Draft.makeWire")
    tries = [
        lambda: maker(points, closed=False, face=False, support=None),
        lambda: maker(points, False, False, None),
        lambda: maker(points, False, False),
        lambda: maker(points, False),
        lambda: maker(points),
    ]
    last_err = None
    for fn in tries:
        try:
            return fn()
        except Exception as ex:
            last_err = ex
    raise RuntimeError(f"No se pudo crear el wire: {last_err}")


def obtener_tablero_y_caras():
    global CARAS_TABLERO_ACTIVAS
    if Gui is None:
        raise RuntimeError("FreeCADGui no esta activo")

    # The user selection defines the panel and optional active faces.
    sel_ex = list(Gui.Selection.getSelectionEx() or [])
    sel_objs = list(Gui.Selection.getSelection() or [])
    tablero = None

    for item in sel_ex:
        if es_tablero(item.Object):
            tablero = item.Object
            break
    if tablero is None:
        for obj in sel_objs:
            if es_tablero(obj):
                tablero = obj
                break
    if tablero is None:
        raise RuntimeError("Seleccione un tablero antes de ejecutar la macro")

    caras = []
    for item in sel_ex:
        if item.Object is not tablero:
            continue
        for sub in list(getattr(item, "SubObjects", []) or []):
            cara = clasificar_cara_desde_face(sub)
            if cara and cara not in caras:
                caras.append(cara)

    CARAS_TABLERO_ACTIVAS = list(caras)
    log_info(f"Panel detectado: {texto_seguro(tablero.Label) or tablero.Name}")
    if caras:
        log_info(f"Caras activas: {', '.join(caras)}")
    else:
        log_info("Caras activas: automaticas")
    return tablero, list(caras)


def resumen_objeto(obj):
    if obj is None:
        return "(ninguno)"
    return texto_seguro(getattr(obj, "Label", "")) or texto_seguro(getattr(obj, "Name", ""))


def resumen_lista_objetos(objs):
    if not objs:
        return "(ninguno)"
    return ", ".join(resumen_objeto(o) for o in objs)


def tablero_y_caras_desde_seleccion():
    if Gui is None:
        return None, []
    try:
        return obtener_tablero_y_caras()
    except Exception:
        return None, []


def rutas_guia_desde_seleccion():
    if Gui is None:
        return []
    rutas = []
    vistos = set()
    for item in list(Gui.Selection.getSelectionEx() or []):
        obj = item.Object
        name = texto_seguro(getattr(obj, "Name", ""))
        if not name or name in vistos:
            continue
        if es_tablero(obj):
            continue
        if es_ruta_guia(obj):
            rutas.append(obj)
            vistos.add(name)
    return rutas


class FormularioConfigV2(object):
    def __init__(self, doc):
        self.doc = doc

    def _move_dialog_to_side(self, dlg, parent):
        if QtWidgets is None:
            return
        try:
            base_geo = parent.frameGeometry() if parent is not None else dlg.frameGeometry()
            screen = None
            if parent is not None and parent.windowHandle() is not None:
                screen = parent.windowHandle().screen()
            if screen is not None:
                avail = screen.availableGeometry()
            else:
                avail = QtWidgets.QApplication.desktop().availableGeometry(parent)  # type: ignore[attr-defined]
            right_x = base_geo.x() + base_geo.width() + 12
            x = min(right_x, avail.right() - dlg.width() - 12)
            y = max(avail.top() + 12, base_geo.y() + 40)
            if x < avail.left() + 12:
                x = max(avail.left() + 12, base_geo.x() - dlg.width() - 12)
            if y + dlg.height() > avail.bottom() - 12:
                y = max(avail.top() + 12, avail.bottom() - dlg.height() - 12)
            dlg.move(x, y)
        except Exception:
            pass

    def run(self):
        if QtWidgets is None:
            log_info("Sin PySide disponible, se usara la seleccion actual")
            tablero, caras = tablero_y_caras_desde_seleccion()
            return {
                "tablero": tablero,
                "caras": caras,
                "rutas": rutas_guia_desde_seleccion(),
                "route_z": DEFAULT_ROUTE_Z,
                "bend_radius": DEFAULT_BEND_RADIUS,
                "separation": DEFAULT_CIRCUIT_SEPARATION,
                "conduit": DEFAULT_CONDUIT,
                "diameter": DEFAULT_DIAMETER,
            }

        parent = Gui.getMainWindow() if Gui is not None else None
        dlg = QtWidgets.QDialog(parent)
        dock = None
        root = None
        lay = None

        if QtCore is not None and parent is not None and hasattr(QtWidgets, "QDockWidget"):
            try:
                old = parent.findChild(QtWidgets.QDockWidget, "ElectricCR_ConectarCajasTableroV2Dock")
                if old is not None:
                    old.close()
                    old.deleteLater()
            except Exception:
                pass
            try:
                dock = QtWidgets.QDockWidget(DEFAULT_PANEL_TITLE, parent)
                dock.setObjectName("ElectricCR_ConectarCajasTableroV2Dock")
                dock.setAllowedAreas(QtCore.Qt.RightDockWidgetArea)
                dock.setMinimumWidth(360)
                dock.setMaximumWidth(460)
                dock.setFeatures(QtWidgets.QDockWidget.DockWidgetClosable)
                try:
                    dock.setFloating(False)
                except Exception:
                    pass
                root = QtWidgets.QWidget(dock)
                dock.setWidget(root)
                parent.addDockWidget(QtCore.Qt.RightDockWidgetArea, dock)
                lay = QtWidgets.QVBoxLayout(root)
            except Exception:
                dock = None
                root = None
                lay = None

        if root is None or lay is None:
            dlg.setWindowTitle(DEFAULT_PANEL_TITLE)
            dlg.resize(460, 420)
            if QtCore is not None:
                dlg.setWindowModality(QtCore.Qt.NonModal)
                dlg.setWindowFlag(QtCore.Qt.Tool, True)
            root = QtWidgets.QWidget(dlg)
            outer = QtWidgets.QVBoxLayout(dlg)
            outer.addWidget(root)
            lay = QtWidgets.QVBoxLayout(root)

        lbl_intro = QtWidgets.QLabel(
            "Seleccione el tablero y opcionalmente una o mas caras del tablero.\n"
            "Seleccione tambien una o mas rutas guia antes de capturar la seleccion."
        )
        lbl_intro.setWordWrap(True)

        grp_tablero = QtWidgets.QGroupBox("Tablero")
        lay_tablero = QtWidgets.QVBoxLayout(grp_tablero)
        lbl_tablero = QtWidgets.QLabel("Tablero: (ninguno)")
        lbl_caras = QtWidgets.QLabel("Caras: automaticas")
        btn_tablero = QtWidgets.QPushButton("Tomar tablero y caras desde seleccion")
        lay_tablero.addWidget(lbl_tablero)
        lay_tablero.addWidget(lbl_caras)
        lay_tablero.addWidget(btn_tablero)

        grp_guias = QtWidgets.QGroupBox("Rutas guia")
        lay_guias = QtWidgets.QVBoxLayout(grp_guias)
        list_guias = QtWidgets.QListWidget()
        list_guias.setMinimumHeight(120)
        btn_guias = QtWidgets.QPushButton("Tomar rutas guia desde seleccion")
        btn_todas = QtWidgets.QPushButton("Usar rutas guia del documento")
        lay_guias.addWidget(list_guias)
        lay_guias.addWidget(btn_guias)
        lay_guias.addWidget(btn_todas)

        grp_param = QtWidgets.QGroupBox("Parametros")
        form = QtWidgets.QFormLayout(grp_param)
        sp_route_z = QtWidgets.QDoubleSpinBox()
        sp_route_z.setRange(-5000.0, 20000.0)
        sp_route_z.setDecimals(1)
        sp_route_z.setSuffix(" mm")
        sp_route_z.setValue(DEFAULT_ROUTE_Z)
        sp_bend = QtWidgets.QDoubleSpinBox()
        sp_bend.setRange(10.0, 1000.0)
        sp_bend.setDecimals(1)
        sp_bend.setSuffix(" mm")
        sp_bend.setValue(DEFAULT_BEND_RADIUS)
        sp_sep = QtWidgets.QDoubleSpinBox()
        sp_sep.setRange(0.0, 5000.0)
        sp_sep.setDecimals(1)
        sp_sep.setSuffix(" mm")
        sp_sep.setValue(DEFAULT_CIRCUIT_SEPARATION)
        form.addRow("Nivel ruta:", sp_route_z)
        form.addRow("Radio curvatura:", sp_bend)
        form.addRow("Separacion circuitos:", sp_sep)

        buttons = QtWidgets.QDialogButtonBox(QtWidgets.QDialogButtonBox.Ok | QtWidgets.QDialogButtonBox.Cancel)

        state = {"tablero": None, "caras": [], "rutas": []}

        def refresh_tablero():
            lbl_tablero.setText(f"Tablero: {resumen_objeto(state['tablero'])}")
            lbl_caras.setText("Caras: " + (", ".join(state["caras"]) if state["caras"] else "automaticas"))

        def refresh_guias():
            list_guias.clear()
            for obj in state["rutas"]:
                list_guias.addItem(resumen_objeto(obj))

        def tomar_tablero():
            tablero, caras = tablero_y_caras_desde_seleccion()
            state["tablero"] = tablero
            state["caras"] = list(caras or [])
            refresh_tablero()

        def tomar_guias():
            state["rutas"] = list(rutas_guia_desde_seleccion())
            refresh_guias()

        def tomar_todas():
            rutas = []
            for obj in list(self.doc.Objects or []):
                if es_ruta_guia(obj):
                    rutas.append(obj)
            state["rutas"] = rutas
            refresh_guias()

        btn_tablero.clicked.connect(tomar_tablero)
        btn_guias.clicked.connect(tomar_guias)
        btn_todas.clicked.connect(tomar_todas)
        buttons.accepted.connect(dlg.accept)
        buttons.rejected.connect(dlg.reject)

        tomar_tablero()
        tomar_guias()

        lay.addWidget(lbl_intro)
        lay.addWidget(grp_tablero)
        lay.addWidget(grp_guias)
        lay.addWidget(grp_param)
        lay.addWidget(buttons)

        if QtCore is None:
            if dlg.exec_() != QtWidgets.QDialog.Accepted:
                return None
        else:
            loop = QtCore.QEventLoop()
            state_result = {"accepted": False}

            def accept_and_close():
                state_result["accepted"] = True
                if dock is not None:
                    dock.close()
                else:
                    dlg.accept()

            def reject_and_close():
                state_result["accepted"] = False
                if dock is not None:
                    dock.close()
                else:
                    dlg.reject()

            try:
                buttons.accepted.disconnect()
            except Exception:
                pass
            try:
                buttons.rejected.disconnect()
            except Exception:
                pass
            buttons.accepted.connect(accept_and_close)
            buttons.rejected.connect(reject_and_close)

            if dock is not None:
                try:
                    dock.visibilityChanged.connect(lambda visible: loop.quit() if not visible else None)
                except Exception:
                    pass
                dock.show()
                try:
                    dock.raise_()
                except Exception:
                    pass
            else:
                dlg.show()
                QtWidgets.QApplication.processEvents()
                self._move_dialog_to_side(dlg, parent)
                try:
                    dlg.raise_()
                    dlg.activateWindow()
                except Exception:
                    pass
                dlg.finished.connect(loop.quit)

            loop.exec_()
            if not bool(state_result["accepted"]):
                return None

        return {
            "tablero": state["tablero"],
            "caras": list(state["caras"] or []),
            "rutas": list(state["rutas"] or []),
            "route_z": float(sp_route_z.value()),
            "bend_radius": float(sp_bend.value()),
            "separation": float(sp_sep.value()),
            "conduit": DEFAULT_CONDUIT,
            "diameter": DEFAULT_DIAMETER,
        }


def obtener_octagonales_por_circuito():
    doc = App.ActiveDocument
    if doc is None:
        return {}
    # Scan the whole document and group octagonal boxes by circuit id.
    out = defaultdict(list)
    for obj in list(doc.Objects or []):
        if not es_octogonal_usable(obj):
            continue
        circuito = obtener_circuito_desde_objeto(obj)
        if not circuito or not circuito_id_valido(circuito):
            log_info(
                "Caja omitida sin circuito valido: {}".format(
                    texto_seguro(getattr(obj, "Label", "")) or texto_seguro(getattr(obj, "Name", ""))
                )
            )
            continue
        out[circuito].append(obj)
    for circuito, cajas in out.items():
        cajas.sort(key=lambda o: natural_key(texto_seguro(getattr(o, "Label", "")) or texto_seguro(getattr(o, "Name", ""))))
        log_info(f"Circuito detectado: {circuito} | cajas={len(cajas)}")
    return dict(out)


def obtener_rutas_guia():
    if Gui is None:
        raise RuntimeError("FreeCADGui no esta activo")
    doc = App.ActiveDocument
    rutas = []
    vistos = set()

    # First try the current selection. This keeps the macro inside user defined channels.
    for item in list(Gui.Selection.getSelectionEx() or []):
        obj = item.Object
        name = texto_seguro(getattr(obj, "Name", ""))
        if not name or name in vistos:
            continue
        if es_tablero(obj):
            continue
        if es_ruta_guia(obj):
            rutas.append(obj)
            vistos.add(name)

    if not rutas and doc is not None:
        # Fallback: find objects named as guide routes already present in the model.
        for obj in list(doc.Objects or []):
            name = texto_seguro(getattr(obj, "Name", ""))
            if not name or name in vistos:
                continue
            txt = f"{texto_seguro(getattr(obj, 'Label', ''))} {texto_seguro(getattr(obj, 'Name', ''))}".lower()
            if "ruta" in txt and "guia" in txt and es_ruta_guia(obj):
                rutas.append(obj)
                vistos.add(name)

    log_info(f"Rutas guia detectadas: {len(rutas)}")
    for ruta in rutas:
        log_info(f"Ruta guia: {texto_seguro(ruta.Label) or ruta.Name}")
    return rutas


def encontrar_ruta_guia_para_octogonal(octogonal, rutas):
    punto = obtener_centro_objeto(octogonal)
    mejor = None
    mejor_d = None
    for ruta in list(rutas or []):
        pts = obtener_puntos_polilinea(ruta)
        proj = project_point_to_polyline_xy(punto, pts)
        if proj is None:
            continue
        d = float(proj["distance"])
        if mejor is None or d < mejor_d:
            mejor = ruta
            mejor_d = d
    if mejor is not None:
        log_info(
            "Ruta guia seleccionada | caja={} | ruta={} | distancia={:.1f} mm".format(
                texto_seguro(getattr(octogonal, "Label", "")) or octogonal.Name,
                texto_seguro(getattr(mejor, "Label", "")) or mejor.Name,
                float(mejor_d),
            )
        )
    return mejor


def ordenar_octagonales_para_evitar_cruces(octagonales):
    return sorted(list(octagonales or []), key=lambda o: float(obtener_centro_objeto(o).y))


def seleccionar_octogonal_origen(cajas, rutas, tablero):
    if not cajas:
        return None
    if len(cajas) == 1:
        return cajas[0]

    # Pick the box that produces the shortest path toward the panel through a guide route.
    mejor = None
    mejor_costo = None
    for caja in cajas:
        ruta = encontrar_ruta_guia_para_octogonal(caja, rutas)
        if ruta is None:
            costo = obtener_centro_objeto(caja).distanceToPoint(obtener_centro_objeto(tablero))
        else:
            pts = obtener_puntos_polilinea(ruta)
            p_caja = obtener_centro_objeto(caja)
            p_tab = punto_panel_mas_cercano(tablero, CARAS_TABLERO_ACTIVAS, p_caja)["punto"]
            pr_caja = project_point_to_polyline_xy(p_caja, pts)
            pr_tab = project_point_to_polyline_xy(p_tab, pts)
            if pr_caja is None or pr_tab is None:
                costo = p_caja.distanceToPoint(p_tab)
            else:
                costo = float(pr_caja["distance"]) + abs(float(pr_tab["s"]) - float(pr_caja["s"])) + float(pr_tab["distance"])
        if mejor is None or costo < mejor_costo:
            mejor = caja
            mejor_costo = costo

    if mejor is not None:
        log_info(
            "Caja origen seleccionada | circuito={} | caja={} | costo={:.1f}".format(
                obtener_circuito_desde_objeto(mejor),
                texto_seguro(getattr(mejor, "Label", "")) or mejor.Name,
                float(mejor_costo),
            )
        )
    return mejor


def construir_ruta_base(octogonal, ruta_guia, tablero, cfg, panel_info_override=None):
    # Build one base route:
    # octogonal -> route z -> guide route -> panel face -> panel.
    route_z = float(cfg.get("route_z", DEFAULT_ROUTE_Z))
    p_caja = obtener_centro_objeto(octogonal)
    p_caja_ruta = vec(p_caja.x, p_caja.y, route_z)
    pts_guia = obtener_puntos_polilinea(ruta_guia)
    if len(pts_guia) < 2:
        raise RuntimeError("La ruta guia no tiene geometria valida")

    panel_info = panel_info_override or punto_panel_mas_cercano(tablero, cfg.get("caras", CARAS_TABLERO_ACTIVAS), p_caja_ruta)
    p_panel = panel_info["punto"]
    p_panel_ruta = vec(p_panel.x, p_panel.y, route_z)

    camino_logico = None
    if NETWORKX_AVAILABLE:
        log_info("NetworkX disponible: se usara para la logica de ruteo")
        camino_logico = ruta_logica_networkx(p_caja_ruta, pts_guia, p_panel_ruta, route_z)
    else:
        log_info("NetworkX no disponible: se usara la logica simple existente")

    if not camino_logico:
        proj_caja = project_point_to_polyline_xy(p_caja_ruta, pts_guia)
        proj_panel = project_point_to_polyline_xy(p_panel_ruta, pts_guia)
        if proj_caja is None or proj_panel is None:
            raise RuntimeError("No se pudo proyectar la ruta base sobre la ruta guia")

        camino_guia = guide_path_between(pts_guia, proj_caja, proj_panel, route_z)
        if not camino_guia:
            raise RuntimeError("No se pudo construir el camino sobre la ruta guia")

        camino_logico = [p_caja_ruta]
        camino_logico.extend(ruta_ortogonal_xy(camino_logico[-1], camino_guia[0], route_z)[1:])
        camino_logico.extend(camino_guia[1:])
        camino_logico.extend(ruta_ortogonal_xy(camino_logico[-1], p_panel_ruta, route_z)[1:])

    pts = [p_caja]
    pts.extend(camino_logico)
    pts.append(p_panel)
    pts = dedup_points(pts)
    log_info(
        "Ruta base construida | caja={} | ruta={} | cara_panel={} | puntos={}".format(
            texto_seguro(getattr(octogonal, "Label", "")) or octogonal.Name,
            texto_seguro(getattr(ruta_guia, "Label", "")) or ruta_guia.Name,
            texto_seguro(panel_info.get("cara", "")) or "Auto",
            len(pts),
        )
    )
    return pts


def aplicar_offset_a_ruta(ruta, offset_mm, route_z):
    puntos = dedup_points(ruta)
    d = float(offset_mm)
    if len(puntos) < 3 or abs(d) <= EPS:
        return puntos

    # Offset only the planar channel segment as a whole wire.
    # This keeps the box and panel end points stable while the routed channel stays parallel.
    ids_planos = [idx for idx, pt in enumerate(puntos) if abs(float(pt.z) - float(route_z)) <= 0.1]
    if len(ids_planos) < 2:
        log_info("Offset aplicado: 0.0 mm (sin tramo plano)")
        return puntos

    i0 = int(ids_planos[0])
    i1 = int(ids_planos[-1])
    base_plana = [vec(pt.x, pt.y, route_z) for pt in puntos[i0:i1 + 1]]
    base_wire = part_wire_from_points(base_plana)
    if base_wire is None:
        log_error("No se pudo crear el wire base para offset")
        return puntos

    dvec = offset_vector_for_points(base_plana, d)
    if dvec.Length <= EPS:
        return puntos

    offset_wire = None
    try:
        if DraftGeomUtils is not None and hasattr(DraftGeomUtils, "offsetWire"):
            offset_wire = DraftGeomUtils.offsetWire(base_wire, dvec)
    except Exception as ex:
        log_error(f"Error aplicando offset: {ex}")

    if offset_wire is None:
        log_error("No se pudo aplicar offset a la ruta")
        return puntos

    offset_pts = points_from_wire(offset_wire, z_override=route_z)
    if len(offset_pts) < 2:
        log_error("Offset invalido: la ruta offset no tiene suficientes puntos")
        return puntos

    out = list(puntos[:i0 + 1])
    if out[-1].distanceToPoint(offset_pts[0]) > 0.1:
        out.append(offset_pts[0])
    for pt in offset_pts[1:-1]:
        out.append(pt)
    if offset_pts[-1].distanceToPoint(puntos[i1]) > 0.1:
        out.append(offset_pts[-1])
    out.extend(list(puntos[i1:]))
    out = dedup_points(out)

    log_info(f"Offset aplicado: {d:.1f} mm")
    return out


def aplicar_curvas_a_ruta(ruta, radio):
    if ruta is None:
        return ruta
    # Draft Wire already supports fillets through FilletRadius.
    try:
        if hasattr(ruta, "FilletRadius"):
            radio = max(0.0, float(radio))
            ruta.FilletRadius = radio
            log_info(f"Curvas aplicadas: radio={radio:.1f} mm")
            return ruta
    except Exception as ex:
        log_error(f"No se pudo asignar FilletRadius: {ex}")
    return ruta


def generar_alimentador(octogonal, ruta_guia, tablero, indice, cfg, panel_info_override=None):
    doc = App.ActiveDocument
    if doc is None:
        raise RuntimeError("No hay documento activo")

    # Channel routing pipeline for one circuit.
    ruta_base = construir_ruta_base(octogonal, ruta_guia, tablero, cfg, panel_info_override=panel_info_override)
    offset_mm = float(indice) * float(cfg.get("separation", DEFAULT_CIRCUIT_SEPARATION))
    ruta_offset = aplicar_offset_a_ruta(ruta_base, offset_mm, float(cfg.get("route_z", DEFAULT_ROUTE_Z)))
    radio_solicitado = float(cfg.get("bend_radius", DEFAULT_BEND_RADIUS))
    radio_efectivo = radio_curva_efectivo(ruta_offset, radio_solicitado)
    if radio_efectivo < radio_solicitado - 0.1:
        log_info(
            "Radio ajustado | caja={} | solicitado={:.1f} mm | efectivo={:.1f} mm".format(
                texto_seguro(getattr(octogonal, "Label", "")) or octogonal.Name,
                radio_solicitado,
                radio_efectivo,
            )
        )

    wire = make_draft_wire(ruta_offset)
    aplicar_curvas_a_ruta(wire, radio_efectivo)

    circuito = obtener_circuito_desde_objeto(octogonal)
    label_caja = texto_seguro(getattr(octogonal, "Label", "")) or octogonal.Name
    label_tab = texto_seguro(getattr(tablero, "Label", "")) or tablero.Name
    conduit_type = texto_seguro(cfg.get("conduit", DEFAULT_CONDUIT)) or DEFAULT_CONDUIT
    diameter = float(cfg.get("diameter", DEFAULT_DIAMETER))
    wire.Label = f"{conduit_type}_{circuito}: {label_caja} -> {label_tab}"

    for ptype, pname, pgroup, pdesc in [
        ("App::PropertyString", "Tipo", "ElectricCR", "Tipo logico"),
        ("App::PropertyString", "ConduitType", "ElectricCR", "Tipo de canalizacion"),
        ("App::PropertyFloat", "DiametroConduit", "ElectricCR", "Diametro"),
        ("App::PropertyString", "CircuitoID", "ElectricCR", "Circuito"),
        ("App::PropertyString", "GeneradoPor", "ElectricCR", "Macro"),
        ("App::PropertyString", "RutaGuiaName", "ElectricCR", "Ruta guia"),
        ("App::PropertyString", "OrigenName", "ElectricCR", "Caja origen"),
        ("App::PropertyString", "DestinoName", "ElectricCR", "Destino"),
        ("App::PropertyInteger", "IndiceCanal", "ElectricCR", "Indice de canal"),
    ]:
        try:
            if pname not in wire.PropertiesList:
                wire.addProperty(ptype, pname, pgroup, pdesc)
        except Exception:
            pass

    try:
        wire.Tipo = "ConduitPath"
        wire.ConduitType = conduit_type
        wire.DiametroConduit = diameter
        wire.CircuitoID = circuito
        wire.GeneradoPor = "Conectar_Cajas_a_Tablero_Auto_v2"
        wire.RutaGuiaName = texto_seguro(getattr(ruta_guia, "Name", ""))
        wire.OrigenName = texto_seguro(getattr(octogonal, "Name", ""))
        wire.DestinoName = texto_seguro(getattr(tablero, "Name", ""))
        wire.IndiceCanal = int(indice)
    except Exception:
        pass

    grupo_circuito = obtener_grupo_circuito(octogonal)
    if grupo_circuito is not None:
        grupo_destino = asegurar_subgrupo(doc, grupo_circuito, f"Alimentadores_{conduit_type}_v2")
        asegurar_objeto_en_grupo(grupo_destino, wire)

    log_info(
        "Alimentador generado | circuito={} | indice={} | caja={} | ruta={}".format(
            circuito,
            int(indice),
            label_caja,
            texto_seguro(getattr(ruta_guia, "Label", "")) or ruta_guia.Name,
        )
    )
    return wire


def conectar_cajas_a_tablero_auto_v2():
    doc = App.ActiveDocument
    if doc is None:
        log_error("No hay documento activo")
        return
    if Gui is None:
        log_error("FreeCADGui no esta activo")
        return

    cfg = FormularioConfigV2(doc).run()
    if cfg is None:
        log_info("Operacion cancelada")
        return
    tablero = cfg.get("tablero")
    caras = list(cfg.get("caras", []) or [])
    rutas = list(cfg.get("rutas", []) or [])
    if tablero is None:
        log_error("No se selecciono un tablero en el formulario")
        return
    CARAS_TABLERO_ACTIVAS[:] = caras

    if not rutas:
        log_error("No se seleccionaron rutas guia en el formulario")
        return

    log_info("Panel detectado: " + resumen_objeto(tablero))
    log_info("Caras activas: " + (", ".join(caras) if caras else "automaticas"))
    log_info("Rutas guia detectadas: " + str(len(rutas)))

    por_circuito = obtener_octagonales_por_circuito()
    if not por_circuito:
        log_error("No se detectaron cajas octogonales")
        return

    items_por_ruta = defaultdict(list)
    for circuito, cajas in sorted(por_circuito.items(), key=lambda it: natural_key(it[0])):
        origen = seleccionar_octogonal_origen(cajas, rutas, tablero)
        if origen is None:
            continue
        ruta = encontrar_ruta_guia_para_octogonal(origen, rutas)
        if ruta is None:
            log_error(f"No se encontro ruta guia para el circuito {circuito}")
            continue
        items_por_ruta[texto_seguro(getattr(ruta, "Name", ""))].append({
            "circuito": circuito,
            "caja": origen,
            "ruta": ruta,
        })

    if not items_por_ruta:
        log_error("No hay circuitos listos para generar alimentadores")
        return

    panel_slots = {}
    if "Top" in caras:
        panel_slots = construir_slots_panel_top(tablero, items_por_ruta, cfg)

    try:
        doc.openTransaction("ElectricCR: Conectar Cajas a Tablero Auto v2")
        generados = 0
        limpiados = set()

        # Each guide route acts as an independent routing channel.
        for ruta_name, items in sorted(items_por_ruta.items(), key=lambda it: natural_key(it[0])):
            items_ordenados = ordenar_items_para_canal(items)
            log_info(f"Ordenando canal {ruta_name} | circuitos={len(items)}")
            for indice, item in enumerate(items_ordenados):
                caja = item["caja"]
                grupo_circuito = obtener_grupo_circuito(caja)
                if grupo_circuito is not None:
                    clave_limpieza = texto_seguro(getattr(grupo_circuito, "Name", ""))
                    if clave_limpieza and clave_limpieza not in limpiados:
                        conduit_type = texto_seguro(cfg.get("conduit", DEFAULT_CONDUIT)) or DEFAULT_CONDUIT
                        grupo_destino = asegurar_subgrupo(doc, grupo_circuito, f"Alimentadores_{conduit_type}_v2")
                        borrados = limpiar_alimentadores_v2(doc, grupo_destino)
                        if borrados:
                            log_info(f"Alimentadores v2 eliminados en {texto_seguro(getattr(grupo_circuito, 'Label', ''))}: {borrados}")
                        limpiados.add(clave_limpieza)
                slot_info = panel_slots.get(texto_seguro(getattr(caja, "Name", "")))
                if slot_info is not None:
                    log_info(
                        "Slot tablero | circuito={} | borde={} | slot={}".format(
                            item["circuito"],
                            texto_seguro(slot_info.get("borde", "")) or "Auto",
                            int(slot_info.get("slot", indice)),
                        )
                    )
                generar_alimentador(item["caja"], item["ruta"], tablero, indice, cfg, panel_info_override=slot_info)
                generados += 1

        doc.recompute()
        doc.commitTransaction()
        log_info(f"Proceso terminado | alimentadores={generados} | rutas_guia={len(items_por_ruta)}")
    except Exception as ex:
        try:
            doc.abortTransaction()
        except Exception:
            pass
        log_error(f"Error general: {ex}")


conectar_cajas_a_tablero_auto_v2()


# FUTURE IMPROVEMENTS
# - better panel face detection
# - smarter route guide selection
# - automatic perpendicular panel entry
# - better conduit crossing detection
# - persistent configuration panel
# - integration into ElectricCR workbench

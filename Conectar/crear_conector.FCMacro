import FreeCAD
import FreeCADGui
import Draft
import os
import sys
_THIS_DIR = os.path.dirname(__file__) if '__file__' in globals() else ''
if _THIS_DIR and _THIS_DIR not in sys.path:
    sys.path.insert(0, _THIS_DIR)
import importlib
import conexiones_grouping as _conexiones_grouping_mod
_conexiones_grouping_mod = importlib.reload(_conexiones_grouping_mod)
ensure_conexiones_group = _conexiones_grouping_mod.ensure_conexiones_group
def _make_wire(points):
    maker = getattr(Draft, "make_wire", None)
    if maker is None:
        maker = getattr(Draft, "makeWire", None)
    if maker is None:
        raise RuntimeError("No se encontro Draft.make_wire ni Draft.makeWire")

    attempts = [
        lambda: maker(points, closed=False, face=False),
        lambda: maker(points, False, False),
        lambda: maker(points, False),
        lambda: maker(points),
    ]
    last_err = None
    for attempt in attempts:
        try:
            return attempt()
        except Exception as ex:
            last_err = ex
    raise RuntimeError(f"No se pudo crear wire: {last_err}")


def crear_conector():
    doc = FreeCAD.ActiveDocument
    if doc is None:
        FreeCAD.Console.PrintError("No hay documento activo.\n")
        return

    selected_objects = FreeCADGui.Selection.getSelection()

    if len(selected_objects) != 2:
        FreeCAD.Console.PrintError("Debe seleccionar exactamente dos objetos para conectar.\n")
        return

    objeto1, objeto2 = selected_objects

    if not hasattr(objeto1, "Shape") or not hasattr(objeto2, "Shape"):
        FreeCAD.Console.PrintError("Ambos objetos deben tener Shape para calcular el centro.\n")
        return

    centro1 = objeto1.Shape.BoundBox.Center
    centro2 = objeto2.Shape.BoundBox.Center

    puntos = [centro1]

    if centro1.x != centro2.x:
        puntos.append(FreeCAD.Vector(centro2.x, centro1.y, centro1.z))

    puntos.append(centro2)

    wire_obj = _make_wire(puntos)
    wire_obj.Label = "Conector"
    grupo_conexiones = ensure_conexiones_group(doc, objects=[objeto1, objeto2])
    try:
        grupo_conexiones.addObject(wire_obj)
    except Exception:
        pass

    doc.recompute()
    FreeCAD.Console.PrintMessage("Conector Draft Wire creado con exito.\n")


# Ejecutar la funcion
crear_conector()

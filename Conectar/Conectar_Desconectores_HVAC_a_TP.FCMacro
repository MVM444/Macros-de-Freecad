# -*- coding: utf-8 -*-
# MenuText: Conectar desconectores asignados (Legacy)
# ToolTip: Resuelve tablero y circuito asignados y delega la geometria al motor general
# Icon: Conectar_Desconectores_HVAC_a_TP.svg
# Toolbar: Conectar Legacy
# Transaction: self

"""Wrapper historico para desconectores HVAC y otros servicios.

La asignacion se resuelve en ``connections.assignments`` y la geometria en
``connections.feeders``. El nombre del archivo se conserva por compatibilidad.
Compatible con FreeCAD 1.1.3. Revision: 2026-08-08.
"""

from pathlib import Path
import re
import runpy
import sys

import FreeCAD as App

try:
    import FreeCADGui as Gui
except Exception:
    Gui = None


TAG = "[ElectricCR][DESCONEXION-ASIGNADA]"


def _services():
    root = Path(__file__).resolve().parent.parent
    if str(root) not in sys.path:
        sys.path.insert(0, str(root))
    from ElectricCR.electriccr.connections import assignments, feeders, panels

    return assignments, feeders, panels


def _is_disconnector(obj):
    assignments, _feeders, panels = _services()
    if obj is None or panels.is_group(obj) or panels.is_library_object(obj):
        return False
    blob = panels.normalized(
        "{} {} {} {}".format(
            getattr(obj, "ClaseEquipo", ""),
            getattr(obj, "Tipo", ""),
            getattr(obj, "ElementType", ""),
            getattr(obj, "IfcType", ""),
        )
    )
    return "desconector" in blob or "disconnect" in blob or "UsoDesconector" in set(getattr(obj, "PropertiesList", []) or [])


def _disconnectors(doc):
    selected = []
    if Gui is not None:
        try:
            selected = [obj for obj in (Gui.Selection.getSelection() or []) if _is_disconnector(obj)]
        except Exception:
            selected = []
    objects = selected or [obj for obj in list(doc.Objects) if _is_disconnector(obj)]
    return sorted({obj.Name: obj for obj in objects}.values(), key=lambda obj: obj.Name)


def analyze_assignments(doc=None, disconnectors=None):
    assignments, _feeders, _panels = _services()
    doc = doc or App.ActiveDocument
    return assignments.analyze_equipment(doc, disconnectors if disconnectors is not None else _disconnectors(doc)) if doc else []


def _natural_key(value):
    _assignments, _feeders, panels = _services()
    parts = re.split(r"(\d+)", panels.text(value))
    return tuple((0, int(part)) if part.isdigit() else (1, panels.normalized(part)) for part in parts)


def _slot_plan(doc):
    records = analyze_assignments(doc, [obj for obj in list(doc.Objects) if _is_disconnector(obj)])
    by_panel = {}
    for record in records:
        if record.get("panel") is not None and record.get("circuit_id"):
            by_panel.setdefault(record["panel"].Name, []).append(record)
    result = {}
    for panel_name, values in by_panel.items():
        values.sort(key=lambda record: (_natural_key(record["circuit_id"]), record["object"].Name))
        for index, record in enumerate(values):
            result[record["object"].Name] = (index, len(values), panel_name)
    return result


def _run_connection(record, slot=None):
    _assignments, feeders, _panels = _services()
    doc = record["object"].Document
    panel = record.get("panel")
    records = [item for item in analyze_assignments(doc) if item.get("panel") is panel and item.get("circuit_id")]
    result = feeders.connect_equipment_feeders(doc, records)
    for route in result.get("routes", []) if result else []:
        if getattr(route, "Destino", None) is record["object"] or getattr(route, "EquipoDestino", None) is record["object"]:
            _apply_legacy_route_schema(route, slot)
            return route
    return None


def _apply_legacy_route_schema(route, slot=None):
    """Conserva propiedades leidas por documentos y pruebas anteriores."""
    definitions = (
        ("App::PropertyInteger", "RanuraTableroOrigen", "Puertos", "Ranura asignada, uno basada"),
        ("App::PropertyInteger", "CantidadRanurasTableroOrigen", "Puertos", "Cantidad de llegadas distribuidas"),
        ("App::PropertyInteger", "FaceIndexTableroOrigen", "Puertos", "Indice de cara superior"),
        ("App::PropertyString", "CaraTableroOrigen", "Puertos", "Cara superior usada"),
    )
    for ptype, name, group, description in definitions:
        if name not in set(getattr(route, "PropertiesList", []) or []):
            route.addProperty(ptype, name, group, description)
    index = int(getattr(route, "SlotTablero", 0) or 0)
    count = int(getattr(route, "CantidadSlotsTablero", 0) or 0)
    if slot:
        index = int(slot[0]) + 1
        count = int(slot[1])
    route.RanuraTableroOrigen = index
    route.CantidadRanurasTableroOrigen = count
    route.FaceIndexTableroOrigen = int(getattr(route, "FaceIndexTablero", 0) or 0)
    route.CaraTableroOrigen = str(getattr(route, "CaraTablero", "Top") or "Top")
    route.Tipo = "AlimentadorEntreTableros"
    return route


def _sheet_get(sheet, cell):
    try:
        return str(sheet.getContents(cell) or "").strip("'")
    except Exception:
        return ""


def _sync_origin_sheet(doc, record):
    _assignments, _feeders, panels = _services()
    sheet = doc.getObject("Red_Origenes")
    if sheet is None:
        return
    row = int(record.get("origin_row", 0) or 0)
    if row <= 0:
        for candidate in range(2, 4000):
            if not _sheet_get(sheet, "E{}".format(candidate)) and not _sheet_get(sheet, "B{}".format(candidate)):
                row = candidate
                break
    if row <= 0:
        return
    obj = record["object"]
    values = (
        "1",
        panels.text(getattr(obj, "Codigo", "")) or panels.text(getattr(obj, "Label", obj.Name)),
        "Desconector",
        panels.panel_code(record["panel"]),
        obj.Name,
        panels.text(getattr(obj, "Label", obj.Name)),
    )
    for index, value in enumerate(values):
        sheet.set("{}{}".format(chr(65 + index), row), panels.text(value))


def _update_schedule(doc):
    macro = Path(__file__).resolve().parent.parent / "Configuracion del proyecto" / "Calculo_Circuitos_PanelSchedule.FCMacro"
    if not macro.exists():
        return None
    namespace = runpy.run_path(str(macro), run_name="electriccr_disconnect_schedule_compat")
    doc.openTransaction("ElectricCR: actualizar tabla de desconectores")
    try:
        result = namespace["run"]()
        doc.recompute()
        doc.commitTransaction()
        return result
    except Exception:
        doc.abortTransaction()
        raise


def run(doc=None, show_dialog=True):
    del show_dialog
    assignments, feeders, panels = _services()
    doc = doc or App.ActiveDocument
    if doc is None:
        return None
    records = analyze_assignments(doc)
    valid = [record for record in records if record.get("panel") is not None and record.get("circuit_id")]
    doc.openTransaction("ElectricCR: sincronizar desconectores asignados")
    try:
        for record in valid:
            assignments.sync_equipment_assignment(record["object"], record["panel"], record["circuit_id"], feeders.GENERATED_BY)
            _sync_origin_sheet(doc, record)
        doc.recompute()
        doc.commitTransaction()
    except Exception:
        doc.abortTransaction()
        raise
    connection_result = feeders.connect_equipment_feeders(doc, records)
    plan = _slot_plan(doc)
    for route in connection_result.get("routes", []) if connection_result else []:
        equipment = getattr(route, "EquipoDestino", None) or getattr(route, "Destino", None)
        _apply_legacy_route_schema(route, plan.get(getattr(equipment, "Name", "")))
    schedule_error = ""
    try:
        _update_schedule(doc)
    except Exception as exc:
        schedule_error = panels.text(exc)
        App.Console.PrintWarning("{} Tabla no actualizada: {}\n".format(TAG, exc))
    return {
        "routes": connection_result.get("routes", []) if connection_result else [],
        "unassigned": [record["object"].Name for record in records if record.get("panel") is None],
        "without_circuit": [record["object"].Name for record in records if not record.get("circuit_id")],
        "errors": (connection_result.get("errors", []) if connection_result else []) + ([schedule_error] if schedule_error else []),
    }


if __name__ == "__main__":
    run()

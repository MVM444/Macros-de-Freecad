# -*- coding: utf-8 -*-
# MenuText: [LEGACY] Conectar Cajas y Alimentadores a Tablero (v1)
# Icon: Conectar/Conectar_Cajas_a_Tablero_Auto.svg
"""
Conecta automaticamente circuitos de tomacorrientes/apagadores hacia cajas octogonales
y al tablero (u objeto ancla) seleccionado.
"""

from pathlib import Path
from collections import defaultdict
from datetime import datetime
import importlib
import json
import math
import os
import re
import sys

import FreeCAD as App
import Draft
try:
    import Part
except Exception:
    Part = None

try:
    import DraftGeomUtils
except Exception:
    DraftGeomUtils = None

try:
    from draftgeoutils import offsets as DraftOffsets
except Exception:
    DraftOffsets = None

try:
    import FreeCADGui as Gui
    GUI_UP = True
except Exception:
    Gui = None
    GUI_UP = False

try:
    from PySide2 import QtWidgets, QtCore
except Exception:
    try:
        from PySide import QtGui as QtWidgets  # type: ignore
        from PySide import QtCore  # type: ignore
    except Exception:
        QtWidgets = None
        QtCore = None


TAG = "[CAJA_TAB_AUTO]"
UI_VERSION = "2026-03-16A"
PARAM_PATH = "User parameter:BaseApp/Preferences/Mod/ElectricCR/ConectarCajasTableroAuto"
DEFAULT_CONDUIT = "EMT"
DEFAULT_DIAMETER = 22.2
DEFAULT_ROUTE_Z = 3000.0
DEFAULT_BEND_RADIUS = 100.0
DEFAULT_FEEDER_AXIS = "Horizontal"
DEFAULT_CIRCUIT_SEPARATION = 50.0
DEFAULT_WALL_OFFSET = 0.0
DEFAULT_FALLBACK_NEAR_MM = 700.0
DEFAULT_DEVICE_LEVEL_TOLERANCE = 10.0
DEFAULT_PORT_STUB = 80.0
EPS = 1e-6
CARDINAL_PORTS = ("North", "South", "East", "West")
BOARD_FACES = ("North", "South", "East", "West", "Top", "Bottom")
OCTAGON_SIDE_PORTS = ("North", "South", "East", "West", "NorthEast", "NorthWest", "SouthEast", "SouthWest")
ANCHOR_FACE_OPTIONS = ("Auto", "North", "South", "East", "West", "Top", "Bottom")
OCTAGON_PORT_TARGETS = (
    ("East", 0.0),
    ("NorthEast", 45.0),
    ("North", 90.0),
    ("NorthWest", 135.0),
    ("West", 180.0),
    ("SouthWest", -135.0),
    ("South", -90.0),
    ("SouthEast", -45.0),
)
STRICT_BACKBONE_CARDINAL = True
ALLOW_DIAGONAL_PORTS_FOR_SWITCH_BOXES = True
RAMAL_LUZ_PATCH_ACTIVE = False
MAX_FEEDER_SPREAD_MM = 600.0
try:
    DEBUG_LOG_PATH = Path(__file__).resolve().with_name("Conectar_Cajas_a_Tablero_Auto.debug.log")
except Exception:
    DEBUG_LOG_PATH = Path.cwd() / "Conectar_Cajas_a_Tablero_Auto.debug.log"
DEBUG_STATE = {
    "enabled": False,
    "path": DEBUG_LOG_PATH,
}


def _log(msg):
    App.Console.PrintMessage(f"{TAG}[INFO] {msg}\n")
    _write_log_line("INFO", msg)


def _warn(msg):
    App.Console.PrintWarning(f"{TAG}[WARN] {msg}\n")
    _write_log_line("WARN", msg)


def _err(msg):
    App.Console.PrintError(f"{TAG}[ERROR] {msg}\n")
    _write_log_line("ERROR", msg)


def _write_log_line(level, msg):
    path = DEBUG_STATE.get("path") or DEBUG_LOG_PATH
    try:
        path = Path(path)
    except Exception:
        path = DEBUG_LOG_PATH
    try:
        path.parent.mkdir(parents=True, exist_ok=True)
        stamp = datetime.now().strftime("%Y-%m-%d %H:%M:%S")
        with path.open("a", encoding="utf-8") as fh:
            fh.write(f"[{stamp}]{TAG}[{_safe_text(level).upper()}] {_safe_text(msg)}\n")
    except Exception:
        pass


def _debug(msg):
    if not bool(DEBUG_STATE.get("enabled", False)):
        return
    _write_log_line("DEBUG", msg)


def _set_debug_enabled(enabled):
    DEBUG_STATE["enabled"] = bool(enabled)


def _debug_log_path():
    try:
        return str(Path(DEBUG_STATE.get("path") or DEBUG_LOG_PATH))
    except Exception:
        return str(DEBUG_LOG_PATH)


def _open_debug_log():
    path = Path(_debug_log_path())
    try:
        path.parent.mkdir(parents=True, exist_ok=True)
        if not path.exists():
            path.touch()
        os.startfile(str(path))  # type: ignore[attr-defined]
    except Exception as ex:
        _warn(f"No se pudo abrir el log: {ex}")


def _start_debug_session(cfg, selection_ctx=None):
    _write_log_line("INFO", "-" * 72)
    _write_log_line("INFO", f"Nueva ejecucion de Conectar Cajas a Tablero (Auto) v{UI_VERSION}.")
    _write_log_line(
        "INFO",
        (
            f"DebugDetallado={'SI' if DEBUG_STATE.get('enabled', False) else 'NO'} "
            f"Conduit={_safe_text(cfg.get('conduit_type', DEFAULT_CONDUIT)).upper()} "
            f"Diametro={float(cfg.get('diameter', DEFAULT_DIAMETER)):.1f} "
            f"RutaZ={float(cfg.get('route_z', DEFAULT_ROUTE_Z)):.1f} "
            f"Radio={float(cfg.get('bend_radius', DEFAULT_BEND_RADIUS)):.1f} "
            f"Perimetro={'SI' if cfg.get('route_by_perimeter', True) else 'NO'} "
            f"Tablero={_safe_text(cfg.get('anchor_name', '')) or '(sin tablero)'} "
            f"CaraTablero={_safe_text(cfg.get('anchor_face', 'Auto')) or 'Auto'} "
            f"CarasPermitidas={','.join(_anchor_allowed_faces(cfg))} "
            f"OrdenManualCircuitos={'SI' if cfg.get('manual_circuit_order_enabled', False) else 'NO'} "
            f"OrdenManualSecciones={'SI' if cfg.get('manual_guide_order_enabled', False) else 'NO'} "
            f"OrdenManualPorSeccion={'SI' if cfg.get('manual_section_circuit_order_enabled', False) else 'NO'} "
            f"OverridesSeccion={len(cfg.get('manual_section_override_map', {}) or {})} "
            f"DirectaMismaCota={'SI' if cfg.get('direct_same_level_only', True) else 'NO'} "
            f"TolCota={float(cfg.get('device_level_tolerance', DEFAULT_DEVICE_LEVEL_TOLERANCE)):.1f} "
            f"RutasGuia={len(cfg.get('guide_names', []) or [])} "
            f"ActualizarRutas={'SI' if cfg.get('refresh_existing_routes', False) else 'NO'}"
        ),
    )
    if selection_ctx:
        groups = selection_ctx.get("groups") or []
        _write_log_line(
            "INFO",
            f"Seleccion inicial: grupos={len(groups)} ancla={'SI' if selection_ctx.get('anchor') is not None else 'NO'}",
        )


def _safe_text(value):
    try:
        return str(value or "")
    except Exception:
        return ""


def _to_float(value, default=0.0):
    try:
        if hasattr(value, "Value"):
            return float(value.Value)
        return float(value)
    except Exception:
        return float(default)


def _safe_name_token(value, fallback="X"):
    txt = _safe_text(value).strip()
    if not txt:
        return fallback
    txt = re.sub(r"[^0-9A-Za-z_]+", "_", txt)
    txt = re.sub(r"_+", "_", txt).strip("_")
    return txt or fallback


def _vec(x=0.0, y=0.0, z=0.0):
    try:
        return App.Vector(float(x), float(y), float(z))
    except Exception:
        return App.Vector(0.0, 0.0, 0.0)


def _fmt_vec(v):
    if v is None:
        return "(None)"
    try:
        return f"({float(v.x):.1f}, {float(v.y):.1f}, {float(v.z):.1f})"
    except Exception:
        return "(?)"


def _fmt_points(points):
    return "[" + ", ".join(_fmt_vec(p) for p in (points or [])) + "]"


def _vlen(v):
    try:
        return float(v.Length)
    except Exception:
        return 0.0


def _normalize(v):
    n = _vlen(v)
    if n <= EPS:
        return _vec(0.0, 0.0, 0.0)
    return _vec(v.x / n, v.y / n, v.z / n)


def _dot(a, b):
    return (float(a.x) * float(b.x)) + (float(a.y) * float(b.y)) + (float(a.z) * float(b.z))


def _effective_fillet_radius(points, requested_radius):
    req = max(0.0, float(requested_radius))
    if req <= EPS:
        return 0.0
    seg_lens = []
    pts = _dedup_points(points)
    for a, b in zip(pts[:-1], pts[1:]):
        d = a.distanceToPoint(b)
        if d > 0.1:
            seg_lens.append(float(d))
    if not seg_lens:
        return 0.0
    limit = max(0.0, min(seg_lens) * 0.45)
    if limit <= EPS:
        return 0.0
    return min(req, limit)


def _angle_deg_xy(vec):
    return math.degrees(math.atan2(float(vec.y), float(vec.x)))


def _circular_distance_deg(a, b):
    d = abs(float(a) - float(b)) % 360.0
    return 360.0 - d if d > 180.0 else d


def _prefs():
    try:
        return App.ParamGet(PARAM_PATH)
    except Exception:
        return None


def _pref_get_bool(key, default):
    p = _prefs()
    if p is None:
        return bool(default)
    try:
        return bool(p.GetBool(str(key), bool(default)))
    except Exception:
        return bool(default)


def _pref_get_float(key, default):
    p = _prefs()
    if p is None:
        return float(default)
    try:
        return float(p.GetFloat(str(key), float(default)))
    except Exception:
        return float(default)


def _pref_get_str(key, default):
    p = _prefs()
    if p is None:
        return str(default)
    try:
        return str(p.GetString(str(key), str(default)))
    except Exception:
        return str(default)


def _json_list(raw):
    try:
        data = json.loads(_safe_text(raw))
        if isinstance(data, list):
            return [_safe_text(x).strip() for x in data if _safe_text(x).strip()]
    except Exception:
        pass
    return []


def _json_dict_of_lists(raw):
    try:
        data = json.loads(_safe_text(raw))
        if isinstance(data, dict):
            out = {}
            for k, vals in data.items():
                key = _safe_text(k).strip()
                if not key:
                    continue
                if isinstance(vals, list):
                    out[key] = [_safe_text(x).strip() for x in vals if _safe_text(x).strip()]
            return out
    except Exception:
        pass
    return {}


def _json_dict_of_str(raw):
    try:
        data = json.loads(_safe_text(raw))
        if isinstance(data, dict):
            out = {}
            for k, v in data.items():
                key = _safe_text(k).strip()
                val = _safe_text(v).strip()
                if key and val:
                    out[key] = val
            return out
    except Exception:
        pass
    return {}


def _save_config(cfg):
    p = _prefs()
    if p is None:
        return
    try:
        p.SetString("anchor_name", _safe_text(cfg.get("anchor_name", "")))
        p.SetString("anchor_face", _safe_text(cfg.get("anchor_face", "Auto")))
        p.SetString("anchor_faces_json", json.dumps(list(cfg.get("anchor_faces", list(BOARD_FACES))) or list(BOARD_FACES), ensure_ascii=True))
        p.SetString("guide_names_json", json.dumps(list(cfg.get("guide_names", []) or []), ensure_ascii=True))
        p.SetString("manual_circuit_order_json", json.dumps(list(cfg.get("manual_circuit_order", []) or []), ensure_ascii=True))
        p.SetBool("manual_circuit_order_enabled", bool(cfg.get("manual_circuit_order_enabled", False)))
        p.SetString("manual_guide_order_json", json.dumps(list(cfg.get("manual_guide_order", []) or []), ensure_ascii=True))
        p.SetBool("manual_guide_order_enabled", bool(cfg.get("manual_guide_order_enabled", False)))
        p.SetString("manual_section_circuit_order_json", json.dumps(dict(cfg.get("manual_section_circuit_order_map", {}) or {}), ensure_ascii=True))
        p.SetBool("manual_section_circuit_order_enabled", bool(cfg.get("manual_section_circuit_order_enabled", False)))
        p.SetString("manual_section_override_json", json.dumps(dict(cfg.get("manual_section_override_map", {}) or {}), ensure_ascii=True))
        p.SetString("conduit_type", _safe_text(cfg.get("conduit_type", DEFAULT_CONDUIT)))
        p.SetFloat("diameter", float(cfg.get("diameter", DEFAULT_DIAMETER)))
        p.SetFloat("route_z", float(cfg.get("route_z", DEFAULT_ROUTE_Z)))
        p.SetFloat("bend_radius", float(cfg.get("bend_radius", DEFAULT_BEND_RADIUS)))
        p.SetString("feeder_axis", _safe_text(cfg.get("feeder_axis", DEFAULT_FEEDER_AXIS)))
        p.SetBool("include_apagadores", bool(cfg.get("include_apagadores", True)))
        p.SetBool("fallback_missing_box", bool(cfg.get("fallback_missing_box", True)))
        p.SetBool("direct_same_level_only", bool(cfg.get("direct_same_level_only", True)))
        p.SetFloat("device_level_tolerance", float(cfg.get("device_level_tolerance", DEFAULT_DEVICE_LEVEL_TOLERANCE)))
        p.SetBool("connect_to_board", bool(cfg.get("connect_to_board", True)))
        p.SetBool("orthogonal_route", bool(cfg.get("orthogonal_route", True)))
        p.SetBool("route_by_perimeter", bool(cfg.get("route_by_perimeter", True)))
        p.SetFloat("wall_margin", float(cfg.get("wall_margin", DEFAULT_WALL_OFFSET)))
        p.SetFloat("circuit_separation", float(cfg.get("circuit_separation", DEFAULT_CIRCUIT_SEPARATION)))
        p.SetBool("reserve_ports", bool(cfg.get("reserve_ports", True)))
        p.SetBool("skip_existing", bool(cfg.get("skip_existing", True)))
        p.SetBool("debug_enabled", bool(cfg.get("debug_enabled", True)))
    except Exception:
        pass


def _default_config():
    sep = _pref_get_float("circuit_separation", DEFAULT_CIRCUIT_SEPARATION)
    if abs(float(sep) - 120.0) <= 1e-9:
        sep = float(DEFAULT_CIRCUIT_SEPARATION)
    return {
        "anchor_name": _pref_get_str("anchor_name", ""),
        "anchor_face": _pref_get_str("anchor_face", "Auto") or "Auto",
        "anchor_faces": _json_list(_pref_get_str("anchor_faces_json", json.dumps(list(BOARD_FACES), ensure_ascii=True))) or list(BOARD_FACES),
        "guide_names": _json_list(_pref_get_str("guide_names_json", "[]")),
        "manual_circuit_order": _json_list(_pref_get_str("manual_circuit_order_json", "[]")),
        "manual_circuit_order_enabled": _pref_get_bool("manual_circuit_order_enabled", False),
        "manual_guide_order": _json_list(_pref_get_str("manual_guide_order_json", "[]")),
        "manual_guide_order_enabled": _pref_get_bool("manual_guide_order_enabled", False),
        "manual_section_circuit_order_map": _json_dict_of_lists(_pref_get_str("manual_section_circuit_order_json", "{}")),
        "manual_section_circuit_order_enabled": _pref_get_bool("manual_section_circuit_order_enabled", False),
        "manual_section_override_map": _json_dict_of_str(_pref_get_str("manual_section_override_json", "{}")),
        "conduit_type": _pref_get_str("conduit_type", DEFAULT_CONDUIT) or DEFAULT_CONDUIT,
        "diameter": _pref_get_float("diameter", DEFAULT_DIAMETER),
        "route_z": _pref_get_float("route_z", DEFAULT_ROUTE_Z),
        "bend_radius": _pref_get_float("bend_radius", DEFAULT_BEND_RADIUS),
        "feeder_axis": _pref_get_str("feeder_axis", DEFAULT_FEEDER_AXIS) or DEFAULT_FEEDER_AXIS,
        "include_apagadores": _pref_get_bool("include_apagadores", True),
        "fallback_missing_box": _pref_get_bool("fallback_missing_box", True),
        "direct_same_level_only": _pref_get_bool("direct_same_level_only", True),
        "device_level_tolerance": _pref_get_float("device_level_tolerance", DEFAULT_DEVICE_LEVEL_TOLERANCE),
        "connect_to_board": _pref_get_bool("connect_to_board", True),
        "orthogonal_route": _pref_get_bool("orthogonal_route", True),
        "route_by_perimeter": _pref_get_bool("route_by_perimeter", True),
        "wall_margin": _pref_get_float("wall_margin", DEFAULT_WALL_OFFSET),
        "circuit_separation": float(sep),
        "reserve_ports": _pref_get_bool("reserve_ports", True),
        "skip_existing": _pref_get_bool("skip_existing", True),
        "debug_enabled": _pref_get_bool("debug_enabled", True),
    }


def _config_dialog_qss():
    return """
QWidget#CajaTabAutoRoot {
    background: #f4f7fb;
}
QGroupBox {
    border: 1px solid #c8d2e1;
    border-radius: 8px;
    margin-top: 12px;
    background: #ffffff;
    font-weight: 600;
}
QGroupBox::title {
    subcontrol-origin: margin;
    left: 10px;
    padding: 0 4px 0 4px;
    color: #1d3d6b;
}
QTabWidget::pane {
    border: 1px solid #b7c6da;
    border-radius: 8px;
    background: #ffffff;
}
QTabBar::tab {
    background: #dfe8f5;
    border: 1px solid #b7c6da;
    border-bottom: none;
    border-top-left-radius: 6px;
    border-top-right-radius: 6px;
    min-width: 110px;
    padding: 6px 10px;
    margin-right: 2px;
}
QTabBar::tab:selected {
    background: #ffffff;
    color: #1b4577;
}
QLabel {
    color: #1f2d3d;
}
QPushButton {
    background: #2d6fb8;
    color: white;
    border-radius: 5px;
    padding: 5px 10px;
}
QPushButton:hover {
    background: #255f9d;
}
QComboBox, QDoubleSpinBox, QSpinBox, QLineEdit {
    border: 1px solid #b7c6da;
    border-radius: 4px;
    padding: 2px 4px;
    background: #ffffff;
}
"""


def _candidate_anchor_objects(doc):
    out = []
    seen = set()
    for obj in getattr(doc, "Objects", []) or []:
        if obj is None or _is_group(obj):
            continue
        name = _safe_text(getattr(obj, "Name", "")).strip()
        if not name or name in seen:
            continue
        txt = f"{_safe_text(getattr(obj, 'Label', ''))} {_safe_text(getattr(obj, 'Name', ''))} {_safe_text(getattr(obj, 'Tipo', ''))}".lower()
        ctype = _fallback_component_type(obj)
        if ctype == "Tablero":
            pri = 0
        elif _is_octagon_box(obj):
            pri = 1
        elif hasattr(obj, "PuertosJSON"):
            pri = 2
        elif any(tok in txt for tok in ("conduit", "emt", "pvc", "tuber", "canal", "ducto", "charola")):
            pri = 3
        else:
            continue
        seen.add(name)
        if not hasattr(obj, "Placement") and not hasattr(obj, "Shape"):
            continue
        out.append((pri, obj))

    def _rank(item):
        pri, obj = item
        return (pri, _safe_text(getattr(obj, "Label", "")).lower(), _safe_text(getattr(obj, "Name", "")).lower())

    out.sort(key=_rank)
    return [obj for _pri, obj in out]


def _polyline_points_from_object(obj):
    if obj is None or _is_group(obj):
        return []
    try:
        shape = getattr(obj, "Shape", None)
    except Exception:
        shape = None
    if shape is None:
        return []
    try:
        if shape.isNull():
            return []
    except Exception:
        pass

    candidates = []
    try:
        for wire in (getattr(shape, "Wires", []) or []):
            pts = []
            for vtx in (getattr(wire, "OrderedVertexes", []) or []):
                pt = getattr(vtx, "Point", None)
                if pt is not None:
                    pts.append(_vec(pt.x, pt.y, pt.z))
            if len(pts) >= 2:
                candidates.append(_dedup_points(pts))
    except Exception:
        pass

    if candidates:
        candidates.sort(key=lambda pts: len(pts), reverse=True)
        return candidates[0]

    try:
        pts = []
        for vtx in (getattr(shape, "OrderedVertexes", []) or []):
            pt = getattr(vtx, "Point", None)
            if pt is not None:
                pts.append(_vec(pt.x, pt.y, pt.z))
        if len(pts) >= 2:
            return _dedup_points(pts)
    except Exception:
        pass

    try:
        pts = []
        for vtx in (getattr(shape, "Vertexes", []) or []):
            pt = getattr(vtx, "Point", None)
            if pt is not None:
                pts.append(_vec(pt.x, pt.y, pt.z))
        if len(pts) >= 2:
            return _dedup_points(pts)
    except Exception:
        pass
    return []


def _is_guide_route_candidate(obj):
    pts = _polyline_points_from_object(obj)
    if len(pts) < 2:
        return False
    try:
        if pts[0].distanceToPoint(pts[-1]) <= 0.1:
            return False
    except Exception:
        pass
    return True


def _candidate_guide_objects(doc):
    out = []
    seen = set()
    for obj in getattr(doc, "Objects", []) or []:
        if obj is None or _is_group(obj):
            continue
        name = _safe_text(getattr(obj, "Name", "")).strip()
        if not name or name in seen:
            continue
        if not _is_guide_route_candidate(obj):
            continue
        seen.add(name)
        out.append(obj)
    out.sort(key=lambda o: (_safe_text(getattr(o, "Label", "")).lower(), _safe_text(getattr(o, "Name", "")).lower()))
    return out


def _object_display_text(obj):
    label = _safe_text(getattr(obj, "Label", "")) or _safe_text(getattr(obj, "Name", ""))
    name = _safe_text(getattr(obj, "Name", ""))
    return f"{label} ({name})"


def _selection_summary_text(selection_ctx):
    ctx = selection_ctx or {}
    sel = list(ctx.get("selection") or [])
    groups = list(ctx.get("groups") or [])
    selection_anchor = ctx.get("selection_anchor")
    persisted_anchor = ctx.get("anchor")
    if not sel:
        if persisted_anchor is not None:
            return (
                "Sin seleccion actual. Se usara el documento completo, salvo que elija grupos manualmente "
                f"desde el arbol. Tablero/ancla persistente: {_object_display_text(persisted_anchor)}."
            )
        return "Sin seleccion actual. Se usara el documento completo, salvo que elija grupos manualmente desde el arbol."

    parts = [f"Seleccion actual: {len(sel)} objeto(s)."]
    if groups:
        parts.append(f"Circuitos inferidos: {len(groups)}.")
    else:
        parts.append("Sin circuitos inferidos desde la seleccion.")
    if selection_anchor is not None:
        parts.append(f"Ancla/tablero detectado en la seleccion: {_object_display_text(selection_anchor)}.")
    elif persisted_anchor is not None:
        parts.append(f"Tablero/ancla persistente: {_object_display_text(persisted_anchor)}.")
    else:
        parts.append("Sin tablero/ancla detectado en la seleccion.")
    parts.append("Si selecciona una toma o apagador, se procesara su grupo de circuito.")
    return " ".join(parts)


class _ConfigDialog(object):
    def __init__(self, doc, selection_ctx):
        self.doc = doc
        self.selection_ctx = selection_ctx or {}
        self.anchor_items = _candidate_anchor_objects(doc)
        # El orden manual es global al documento, no solo al alcance actual.
        self.circuit_items = _candidate_circuit_groups(doc, [])

    def _set_combo_name(self, combo, name):
        want = _safe_text(name).strip()
        if not want:
            return
        for i in range(combo.count()):
            if _safe_text(combo.itemData(i)).strip() == want:
                combo.setCurrentIndex(i)
                return

    def _ensure_combo_has_object(self, combo, obj):
        if obj is None:
            return
        name = _safe_text(getattr(obj, "Name", "")).strip()
        if not name:
            return
        for i in range(combo.count()):
            if _safe_text(combo.itemData(i)).strip() == name:
                combo.setCurrentIndex(i)
                return
        combo.addItem(_object_display_text(obj), name)
        combo.setCurrentIndex(combo.count() - 1)

    def _current_selection_object(self):
        sel = _selection_objects()
        if sel:
            return sel[0]
        return None

    def _current_selection_objects(self):
        return list(_selection_objects() or [])

    def _board_face_from_subshape(self, obj, subshape):
        if obj is None or subshape is None:
            return ""
        try:
            u0, u1, v0, v1 = subshape.ParameterRange
            normal = subshape.normalAt(0.5 * (u0 + u1), 0.5 * (v0 + v1))
        except Exception:
            normal = None
        if normal is not None:
            try:
                nx = float(normal.x)
                ny = float(normal.y)
                nz = float(normal.z)
                ax = abs(nx)
                ay = abs(ny)
                az = abs(nz)
                if az >= ax and az >= ay and az > 0.25:
                    return "Top" if nz > 0.0 else "Bottom"
                if ax >= ay and ax > 0.25:
                    return "East" if nx > 0.0 else "West"
                if abs(ny) > 0.25:
                    return "North" if ny > 0.0 else "South"
            except Exception:
                pass
        try:
            obj_bb = getattr(getattr(obj, "Shape", None), "BoundBox", None)
            face_bb = getattr(subshape, "BoundBox", None)
            if obj_bb is None or face_bb is None:
                return ""
            best = min(
                (
                    (abs(float(face_bb.XMin) - float(obj_bb.XMin)), "West"),
                    (abs(float(face_bb.XMax) - float(obj_bb.XMax)), "East"),
                    (abs(float(face_bb.YMin) - float(obj_bb.YMin)), "South"),
                    (abs(float(face_bb.YMax) - float(obj_bb.YMax)), "North"),
                    (abs(float(face_bb.ZMin) - float(obj_bb.ZMin)), "Bottom"),
                    (abs(float(face_bb.ZMax) - float(obj_bb.ZMax)), "Top"),
                ),
                key=lambda it: float(it[0]),
            )
            return best[1]
        except Exception:
            return ""

    def _selection_face_subshape(self, sel_ex, idx, sub_name):
        sub_objs = list(getattr(sel_ex, "SubObjects", []) or [])
        if idx < len(sub_objs) and sub_objs[idx] is not None:
            return sub_objs[idx]
        sobj = getattr(sel_ex, "Object", None)
        shape = getattr(sobj, "Shape", None) if sobj is not None else None
        if shape is None:
            return None
        try:
            return shape.getElement(_safe_text(sub_name).strip())
        except Exception:
            return None

    def _selection_anchor_face_pick(self):
        picks = []
        for sel_ex in (_selection_ex() or []):
            sobj = getattr(sel_ex, "Object", None)
            if sobj is None:
                continue
            sub_names = list(getattr(sel_ex, "SubElementNames", []) or [])
            faces = []
            seen = set()
            for idx, sub_name in enumerate(sub_names):
                sub_txt = _safe_text(sub_name).strip()
                if not sub_txt.startswith("Face"):
                    continue
                sub_obj = self._selection_face_subshape(sel_ex, idx, sub_txt)
                face_name = self._board_face_from_subshape(sobj, sub_obj)
                if face_name and face_name not in seen:
                    faces.append(face_name)
                    seen.add(face_name)
            if faces:
                picks.append((0 if _is_board_like(sobj) else 1, sobj, faces))
        if not picks:
            return None, []
        picks.sort(key=lambda it: (int(it[0]), _safe_text(getattr(it[1], "Label", "")).lower(), _safe_text(getattr(it[1], "Name", "")).lower()))
        return picks[0][1], picks[0][2]

    def _selected_anchor_face_names(self, list_widget):
        names = []
        for i in range(list_widget.count()):
            item = list_widget.item(i)
            name = _safe_text(item.data(QtCore.Qt.UserRole) if QtCore else item.text()).strip()
            if name in BOARD_FACES and name not in names:
                names.append(name)
        return names

    def _set_selected_anchor_faces(self, list_widget, faces):
        list_widget.clear()
        seen = set()
        for face_name in (faces or []):
            key = _safe_text(face_name).strip()
            if key not in BOARD_FACES or key in seen:
                continue
            seen.add(key)
            item = QtWidgets.QListWidgetItem(key)
            if QtCore:
                item.setData(QtCore.Qt.UserRole, key)
            list_widget.addItem(item)

    def _anchor_faces_status_text(self, faces):
        vals = [x for x in (faces or []) if _safe_text(x).strip() in BOARD_FACES]
        if not vals:
            return "Caras del tablero activas: automatico (todas)."
        return "Caras del tablero activas: " + ", ".join(vals) + "."

    def _anchor_face_display_text(self, faces):
        vals = [x for x in (faces or []) if _safe_text(x).strip() in BOARD_FACES]
        if not vals:
            return "Automatico (todas)"
        if len(vals) == 1:
            return vals[0]
        return ", ".join(vals)

    def _sync_anchor_face_controls(self, combo_face, list_widget, value_widget=None, label_widget=None):
        vals = self._selected_anchor_face_names(list_widget)
        target = vals[0] if len(vals) == 1 else "Auto"
        idx = max(0, combo_face.findText(target))
        combo_face.setCurrentIndex(idx)
        if value_widget is not None:
            value_widget.setText(self._anchor_face_display_text(vals))
        self._update_anchor_faces_status(label_widget, list_widget)

    def _update_anchor_faces_status(self, label_widget, list_widget):
        if label_widget is None:
            return
        label_widget.setText(self._anchor_faces_status_text(self._selected_anchor_face_names(list_widget)))

    def _apply_anchor_face_selection(self, combo_face, list_widget, faces, value_widget=None, label_widget=None):
        picked = [x for x in (faces or []) if _safe_text(x).strip() in BOARD_FACES]
        if not picked:
            return
        self._set_selected_anchor_faces(list_widget, picked)
        self._sync_anchor_face_controls(combo_face, list_widget, value_widget, label_widget)

    def _assign_anchor_from_selection(self, combo):
        obj = self._current_selection_object()
        if obj is None:
            _warn("No hay seleccion activa para capturar como tablero/ancla.")
            return
        self._ensure_combo_has_object(combo, obj)

    def _assign_anchor_faces_from_selection(self, combo_anchor, combo_face, list_widget, value_widget=None, label_widget=None):
        obj, faces = self._selection_anchor_face_pick()
        if obj is None:
            _warn("No hay seleccion activa para capturar caras de tablero/ancla.")
            return
        self._ensure_combo_has_object(combo_anchor, obj)
        if not faces:
            _warn("Seleccione una o mas caras del tablero/ancla para capturarlas.")
            return
        self._apply_anchor_face_selection(combo_face, list_widget, faces, value_widget, label_widget)
        _log(
            "Caras tablero capturadas: "
            f"{', '.join(faces)} | objeto={_safe_text(getattr(obj, 'Label', '')) or _safe_text(getattr(obj, 'Name', ''))}"
        )

    def _clear_anchor_faces(self, combo_face, list_widget, value_widget=None, label_widget=None):
        self._set_selected_anchor_faces(list_widget, [])
        self._sync_anchor_face_controls(combo_face, list_widget, value_widget, label_widget)

    def _refresh_anchor_list(self, combo):
        current_name = _safe_text(combo.currentData()).strip()
        self.anchor_items = _candidate_anchor_objects(self.doc)
        combo.clear()
        combo.addItem("(Sin tablero/ancla)", "")
        for obj in self.anchor_items:
            combo.addItem(_object_display_text(obj), obj.Name)
        self._set_combo_name(combo, current_name)

    def _selected_guide_names(self, list_widget):
        names = []
        for i in range(list_widget.count()):
            item = list_widget.item(i)
            name = _safe_text(item.data(QtCore.Qt.UserRole) if QtCore else item.text()).strip()
            if name:
                names.append(name)
        return names

    def _set_selected_guides(self, list_widget, names):
        list_widget.clear()
        seen = set()
        for name in (names or []):
            key = _safe_text(name).strip()
            if not key or key in seen:
                continue
            seen.add(key)
            obj = _find_object_by_name(self.doc, key)
            text = _object_display_text(obj) if obj is not None else key
            item = QtWidgets.QListWidgetItem(text)
            if QtCore:
                item.setData(QtCore.Qt.UserRole, key)
            list_widget.addItem(item)

    def _candidate_circuits_for_ui(self):
        groups = _candidate_circuit_groups(self.doc, [])
        if not groups:
            groups = list(self.circuit_items or [])
        self.circuit_items = list(groups or [])
        return self.circuit_items

    def _set_circuit_order(self, list_widget, groups, ordered_ids=None):
        order_ids = [_safe_text(x).strip() for x in (ordered_ids or []) if _safe_text(x).strip()]
        group_map = {}
        for grp in (groups or []):
            gid = _group_id(grp)
            if gid and gid not in group_map:
                group_map[gid] = grp
        ordered = []
        seen = set()
        for gid in order_ids:
            grp = group_map.get(gid)
            if grp is None or gid in seen:
                continue
            ordered.append(grp)
            seen.add(gid)
        leftovers = sorted(
            [grp for gid, grp in group_map.items() if gid not in seen],
            key=lambda g: _natural_key(_circuit_id_for_group(g)),
        )
        ordered.extend(leftovers)
        list_widget.clear()
        for grp in ordered:
            gid = _group_id(grp)
            if not gid:
                continue
            item = QtWidgets.QListWidgetItem(_circuit_id_for_group(grp))
            if QtCore:
                item.setData(QtCore.Qt.UserRole, gid)
            item.setToolTip(gid)
            list_widget.addItem(item)

    def _selected_circuit_order_ids(self, list_widget):
        out = []
        for i in range(list_widget.count()):
            item = list_widget.item(i)
            gid = _safe_text(item.data(QtCore.Qt.UserRole) if QtCore else item.text()).strip()
            if gid:
                out.append(gid)
        return out

    def _refresh_circuit_order(self, list_widget):
        groups = self._candidate_circuits_for_ui()
        current = self._selected_circuit_order_ids(list_widget)
        self._set_circuit_order(list_widget, groups, current)

    def _move_circuit_order(self, list_widget, delta):
        row = list_widget.currentRow()
        if row < 0:
            return
        target = row + int(delta)
        if target < 0 or target >= list_widget.count():
            return
        item = list_widget.takeItem(row)
        list_widget.insertItem(target, item)
        list_widget.setCurrentRow(target)

    def _clear_circuit_order(self, list_widget):
        groups = self._candidate_circuits_for_ui()
        self._set_circuit_order(list_widget, groups, [])

    def _section_display_text(self, section_key):
        key = _safe_text(section_key).strip()
        if not key or key == "AUTO":
            return "AUTO (sin guia)"
        obj = _find_object_by_name(self.doc, key)
        return _object_display_text(obj) if obj is not None else key

    def _selected_section_keys(self, list_widget):
        out = []
        for i in range(list_widget.count()):
            item = list_widget.item(i)
            key = _safe_text(item.data(QtCore.Qt.UserRole) if QtCore else item.text()).strip()
            if key:
                out.append(key)
        return out

    def _set_section_order(self, list_widget, section_keys, ordered_keys=None):
        want = [_safe_text(x).strip() for x in (ordered_keys or []) if _safe_text(x).strip()]
        keys = []
        seen = set()
        for key in (section_keys or []):
            k = _safe_text(key).strip()
            if not k or k in seen:
                continue
            seen.add(k)
            keys.append(k)
        if "AUTO" not in seen:
            keys.append("AUTO")
        out = []
        used = set()
        for key in want:
            if key in keys and key not in used:
                out.append(key)
                used.add(key)
        leftovers = [k for k in keys if k not in used]
        leftovers = sorted(leftovers, key=lambda x: (1 if x == "AUTO" else 0, self._section_display_text(x).lower()))
        out.extend(leftovers)
        list_widget.clear()
        for key in out:
            item = QtWidgets.QListWidgetItem(self._section_display_text(key))
            if QtCore:
                item.setData(QtCore.Qt.UserRole, key)
            item.setToolTip(key)
            list_widget.addItem(item)

    def _set_section_keys_in_combo(self, combo, section_keys):
        current = _safe_text(combo.currentData()).strip()
        combo.blockSignals(True)
        combo.clear()
        seen = set()
        for key in (section_keys or []):
            k = _safe_text(key).strip()
            if not k or k in seen:
                continue
            seen.add(k)
            combo.addItem(self._section_display_text(k), k)
        if combo.count() == 0:
            combo.addItem("AUTO (sin guia)", "AUTO")
        idx = combo.findData(current)
        combo.setCurrentIndex(idx if idx >= 0 else 0)
        combo.blockSignals(False)

    def _selected_section_circuit_ids(self, list_widget):
        out = []
        for i in range(list_widget.count()):
            item = list_widget.item(i)
            gid = _safe_text(item.data(QtCore.Qt.UserRole) if QtCore else item.text()).strip()
            if gid:
                out.append(gid)
        return out

    def _set_section_circuit_order(self, list_widget, items, ordered_ids=None):
        want = [_safe_text(x).strip() for x in (ordered_ids or []) if _safe_text(x).strip()]
        item_map = {}
        for gid, label in (items or []):
            key = _safe_text(gid).strip()
            if key and key not in item_map:
                item_map[key] = _safe_text(label).strip() or key
        ordered = []
        used = set()
        for gid in want:
            if gid in item_map and gid not in used:
                ordered.append((gid, item_map[gid]))
                used.add(gid)
        leftovers = sorted(
            [(gid, label) for gid, label in item_map.items() if gid not in used],
            key=lambda pair: _natural_key(pair[1]),
        )
        ordered.extend(leftovers)
        list_widget.clear()
        for gid, label in ordered:
            item = QtWidgets.QListWidgetItem(label)
            if QtCore:
                item.setData(QtCore.Qt.UserRole, gid)
            item.setToolTip(gid)
            list_widget.addItem(item)

    def _preview_section_circuit_items(self, anchor_name, anchor_face, anchor_faces, guide_names, include_apagadores=True, section_override_map=None):
        board_obj = _find_object_by_name(self.doc, anchor_name)
        guide_objs = [o for o in _objects_by_names(self.doc, guide_names) if _is_guide_route_candidate(o)]
        get_component_type = _import_component_classifier()
        groups = self._candidate_circuits_for_ui()
        section_map = defaultdict(list)
        section_keys = []
        seen_sections = set()
        for key in list(guide_names or []) + ["AUTO"]:
            k = _safe_text(key).strip()
            if not k or k in seen_sections:
                continue
            seen_sections.add(k)
            section_keys.append(k)
        preview_cfg = {
            "fallback_missing_box": True,
            "direct_same_level_only": True,
            "device_level_tolerance": DEFAULT_DEVICE_LEVEL_TOLERANCE,
            "connect_to_board": True,
        }
        for cgroup in groups:
            circuit_id = _circuit_id_for_group(cgroup)
            devices, boxes = _collect_circuit_objects(
                cgroup,
                get_component_type=get_component_type,
                include_apagadores=bool(include_apagadores),
            )
            if not devices and not boxes:
                continue
            box_by_source = _map_boxes_by_source(boxes)
            plan = _build_plan_for_circuit(
                circuit_group=cgroup,
                devices=devices,
                boxes=boxes,
                box_by_source=box_by_source,
                board_obj=board_obj,
                cfg=preview_cfg,
            )
            src_obj = _feeder_source_from_plan(plan)
            section_key = "AUTO"
            if src_obj is not None and board_obj is not None and guide_objs:
                src_pt = _anchor_point(src_obj)
                board_ep = _board_face_endpoint(
                    board_obj,
                    toward_point=src_pt,
                    forced_face=_safe_text(anchor_face).strip() or "Auto",
                    tangent_offset=0.0,
                    allowed_faces=[x for x in (anchor_faces or list(BOARD_FACES)) if _safe_text(x).strip() in BOARD_FACES],
                )
                guide_info = _best_guide_for_pair(
                    src_pt,
                    board_ep.get("point"),
                    guide_objs,
                    offset_vec=_vec(0.0, 0.0, 0.0),
                    offset_scalar=0.0,
                    prefer_start=True,
                )
                if guide_info is not None:
                    section_key = _safe_text(getattr(guide_info.get("obj"), "Name", "")).strip() or "AUTO"
            gid = _group_id(cgroup) or circuit_id
            forced_key = _safe_text(dict(section_override_map or {}).get(gid, "")).strip()
            if forced_key:
                section_key = forced_key
            section_map[section_key].append((gid, circuit_id))
            if section_key not in seen_sections:
                seen_sections.add(section_key)
                section_keys.append(section_key)
        return section_keys, dict(section_map)

    def _assign_guides_from_selection(self, list_widget):
        objs = [o for o in self._current_selection_objects() if _is_guide_route_candidate(o)]
        if not objs:
            _warn("Seleccione una o mas polilineas/wires guia en el plano de trabajo.")
            return
        self._set_selected_guides(list_widget, [_safe_text(getattr(o, "Name", "")) for o in objs])

    def _clear_guides(self, list_widget):
        list_widget.clear()

    def _ensure_root_group(self, name, label=None):
        grp = _find_object_by_name(self.doc, name)
        if grp is None:
            try:
                grp = self.doc.addObject("App::DocumentObjectGroup", name)
            except Exception:
                grp = _find_object_by_name(self.doc, name)
        if grp is not None and label:
            try:
                grp.Label = _safe_text(label)
            except Exception:
                pass
        return grp

    def _rename_and_group_guides(self, list_widget):
        names = self._selected_guide_names(list_widget)
        if not names:
            sel = [o for o in self._current_selection_objects() if _is_guide_route_candidate(o)]
            names = [_safe_text(getattr(o, "Name", "")) for o in sel]
        objs = [o for o in _objects_by_names(self.doc, names) if _is_guide_route_candidate(o)]
        if not objs:
            _warn("No hay rutas guia validas para renombrar/agrupar.")
            return

        objs = sorted(
            objs,
            key=lambda o: (
                _safe_text(getattr(o, "Label", "")).lower(),
                _safe_text(getattr(o, "Name", "")).lower(),
            ),
        )

        g_electrico = self._ensure_root_group("electrico", label="electrico")
        if g_electrico is None:
            _warn("No se pudo crear/encontrar el grupo raiz 'electrico'.")
            return
        g_guides = _ensure_child_group(self.doc, g_electrico, "Rutas_Guia_2D", prefix="RutasGuia")

        new_names = []
        try:
            self.doc.openTransaction("ElectricCR: renombrar y agrupar rutas guia")
        except Exception:
            pass
        try:
            for idx, obj in enumerate(objs, start=1):
                target_name = f"Ruta_Guia_{idx:03d}"
                target_label = f"Ruta Guia {idx:03d}"
                current_name = _safe_text(getattr(obj, "Name", "")).strip()
                if target_name != current_name:
                    probe = target_name
                    salt = 1
                    while True:
                        existing = _find_object_by_name(self.doc, probe)
                        if existing is None or existing is obj:
                            break
                        probe = f"{target_name}_{salt:02d}"
                        salt += 1
                    target_name = probe
                    try:
                        self.doc.renameObject(current_name, target_name)
                    except Exception:
                        pass
                obj2 = _find_object_by_name(self.doc, target_name) or obj
                try:
                    obj2.Label = target_label
                except Exception:
                    pass
                _ensure_in_group(g_guides, obj2)
                new_names.append(_safe_text(getattr(obj2, "Name", "")).strip())
            try:
                self.doc.recompute()
            except Exception:
                pass
            try:
                self.doc.commitTransaction()
            except Exception:
                pass
        except Exception:
            try:
                self.doc.abortTransaction()
            except Exception:
                pass
            raise

        self._set_selected_guides(list_widget, new_names)

    def _move_dialog_to_side(self, dlg, parent):
        if QtCore is None:
            return
        try:
            dlg.adjustSize()
        except Exception:
            pass
        try:
            base_geo = parent.frameGeometry() if parent is not None else dlg.frameGeometry()
            screen = None
            if parent is not None and parent.windowHandle() is not None:
                screen = parent.windowHandle().screen()
            if screen is not None:
                avail = screen.availableGeometry()
            else:
                avail = QtWidgets.QApplication.desktop().availableGeometry(parent)  # type: ignore[attr-defined]
            right_x = base_geo.x() + base_geo.width() + 12
            x = min(right_x, avail.right() - dlg.width() - 12)
            y = max(avail.top() + 12, base_geo.y() + 40)
            if x < avail.left() + 12:
                x = max(avail.left() + 12, base_geo.x() - dlg.width() - 12)
            if y + dlg.height() > avail.bottom() - 12:
                y = max(avail.top() + 12, avail.bottom() - dlg.height() - 12)
            dlg.move(x, y)
        except Exception:
            pass

    def run(self):
        cfg = _default_config()
        if not GUI_UP or QtWidgets is None:
            return cfg

        parent = None
        try:
            parent = Gui.getMainWindow()
        except Exception:
            parent = None

        dlg = QtWidgets.QDialog(parent)
        dock = None
        root = None
        lay = None
        if QtCore is not None and parent is not None and hasattr(QtWidgets, "QDockWidget"):
            try:
                old = parent.findChild(QtWidgets.QDockWidget, "ElectricCR_ConectarCajasTableroDock")
                if old is not None:
                    old.close()
                    old.deleteLater()
            except Exception:
                pass
            try:
                dock = QtWidgets.QDockWidget(f"Conectar Cajas a Tablero (Auto) v{UI_VERSION}", parent)
                dock.setObjectName("ElectricCR_ConectarCajasTableroDock")
                # Mantener el panel fijo evita caidas al arrastrar/flotar el dock
                # en algunas instalaciones de FreeCAD/PySide.
                dock.setAllowedAreas(QtCore.Qt.RightDockWidgetArea)
                dock.setMinimumWidth(440)
                dock.setMaximumWidth(540)
                dock.setFeatures(QtWidgets.QDockWidget.DockWidgetClosable)
                try:
                    dock.setFloating(False)
                except Exception:
                    pass
                root = QtWidgets.QWidget(dock)
                root.setObjectName("CajaTabAutoRoot")
                root.setStyleSheet(_config_dialog_qss())
                dock.setWidget(root)
                parent.addDockWidget(QtCore.Qt.RightDockWidgetArea, dock)
                lay = QtWidgets.QVBoxLayout(root)
            except Exception:
                dock = None
                root = None
                lay = None

        if root is None or lay is None:
            dlg.setWindowTitle(f"Conectar Cajas a Tablero (Auto) v{UI_VERSION}")
            dlg.setMinimumWidth(500)
            if QtCore is not None:
                dlg.setWindowModality(QtCore.Qt.NonModal)
                dlg.setWindowFlag(QtCore.Qt.Tool, True)
            root = QtWidgets.QWidget(dlg)
            root.setObjectName("CajaTabAutoRoot")
            root.setStyleSheet(_config_dialog_qss())
            outer = QtWidgets.QVBoxLayout(dlg)
            outer.addWidget(root)
            lay = QtWidgets.QVBoxLayout(root)

        hdr = QtWidgets.QLabel(
            f"v{UI_VERSION} | "
            "Conecta por circuito: dispositivo->caja (si existe), "
            "cajas entre si y alimentador al tablero o ancla seleccionada."
        )
        hdr.setWordWrap(True)

        lbl_selection = QtWidgets.QLabel(_selection_summary_text(self.selection_ctx))
        lbl_selection.setWordWrap(True)
        lbl_selection.setStyleSheet("color:#4b5563;")

        tabs = QtWidgets.QTabWidget()

        tab_scope = QtWidgets.QWidget()
        lay_scope = QtWidgets.QVBoxLayout(tab_scope)

        grp_scope = QtWidgets.QGroupBox("Tablero / Ancla")
        form_scope = QtWidgets.QFormLayout(grp_scope)
        cmb_anchor = QtWidgets.QComboBox()
        cmb_anchor.addItem("(Sin tablero/ancla)", "")
        for obj in self.anchor_items:
            cmb_anchor.addItem(_object_display_text(obj), obj.Name)

        preselected_anchor = self.selection_ctx.get("anchor")
        if preselected_anchor is not None:
            self._ensure_combo_has_object(cmb_anchor, preselected_anchor)
        else:
            self._set_combo_name(cmb_anchor, _safe_text(cfg.get("anchor_name", "")))

        chk_board = QtWidgets.QCheckBox("Conectar circuito al tablero/ancla seleccionado")
        chk_board.setChecked(bool(cfg.get("connect_to_board", True)))
        cmb_anchor_face = QtWidgets.QComboBox()
        cmb_anchor_face.addItems(list(ANCHOR_FACE_OPTIONS))
        face_txt = _safe_text(cfg.get("anchor_face", "Auto")).strip() or "Auto"
        face_idx = max(0, cmb_anchor_face.findText(face_txt))
        cmb_anchor_face.setCurrentIndex(face_idx)
        txt_anchor_face = QtWidgets.QLineEdit()
        txt_anchor_face.setReadOnly(True)
        form_scope.addRow("Tablero / ancla:", cmb_anchor)
        form_scope.addRow("Cara(s) seleccionada(s):", txt_anchor_face)
        form_scope.addRow("", chk_board)

        grp_anchor_faces = QtWidgets.QGroupBox("Caras del tablero para alimentadores")
        lay_anchor_faces = QtWidgets.QVBoxLayout(grp_anchor_faces)
        list_anchor_faces = QtWidgets.QListWidget()
        list_anchor_faces.setSelectionMode(QtWidgets.QAbstractItemView.ExtendedSelection)
        list_anchor_faces.setMinimumHeight(60)
        selected_anchor_faces = [
            _safe_text(x).strip()
            for x in (cfg.get("anchor_faces", []) or [])
            if _safe_text(x).strip() in BOARD_FACES
        ]
        if not selected_anchor_faces and face_txt in BOARD_FACES:
            selected_anchor_faces = [face_txt]
        if len(selected_anchor_faces) == len(BOARD_FACES):
            selected_anchor_faces = []
        self._set_selected_anchor_faces(list_anchor_faces, selected_anchor_faces)

        anchor_face_buttons = QtWidgets.QGridLayout()
        btn_pick_anchor_faces = QtWidgets.QPushButton("Tomar seleccion -> Caras tablero")
        btn_clear_anchor_faces = QtWidgets.QPushButton("Usar todas las caras")
        anchor_face_buttons.addWidget(btn_pick_anchor_faces, 0, 0)
        anchor_face_buttons.addWidget(btn_clear_anchor_faces, 0, 1)

        note_anchor_faces = QtWidgets.QLabel(
            "Seleccione una o mas Face del tablero/ancla. Vacio = todas las caras permitidas automaticamente."
        )
        note_anchor_faces.setWordWrap(True)
        note_anchor_faces.setStyleSheet("color:#4b5563;")
        lbl_anchor_faces_state = QtWidgets.QLabel("")
        lbl_anchor_faces_state.setWordWrap(True)
        lbl_anchor_faces_state.setStyleSheet("color:#1f2937;")

        lay_anchor_faces.addWidget(list_anchor_faces)
        lay_anchor_faces.addLayout(anchor_face_buttons)
        lay_anchor_faces.addWidget(note_anchor_faces)
        lay_anchor_faces.addWidget(lbl_anchor_faces_state)
        self._sync_anchor_face_controls(cmb_anchor_face, list_anchor_faces, txt_anchor_face, lbl_anchor_faces_state)

        sel_box = QtWidgets.QGroupBox("Seleccion con ventana abierta")
        sel_grid = QtWidgets.QGridLayout(sel_box)
        btn_pick_anchor = QtWidgets.QPushButton("Tomar seleccion -> Tablero/Ancla")
        btn_refresh = QtWidgets.QPushButton("Refrescar lista")
        sel_grid.addWidget(btn_pick_anchor, 0, 0)
        sel_grid.addWidget(btn_refresh, 0, 1)

        grp_guides = QtWidgets.QGroupBox("Rutas guia de alimentadores")
        lay_guides = QtWidgets.QVBoxLayout(grp_guides)
        list_guides = QtWidgets.QListWidget()
        list_guides.setSelectionMode(QtWidgets.QAbstractItemView.ExtendedSelection)
        list_guides.setMinimumHeight(72)
        self._set_selected_guides(list_guides, cfg.get("guide_names", []))

        guide_buttons = QtWidgets.QGridLayout()
        btn_pick_guides = QtWidgets.QPushButton("Tomar seleccion -> Rutas guia")
        btn_clear_guides = QtWidgets.QPushButton("Limpiar rutas guia")
        btn_rename_guides = QtWidgets.QPushButton("Renombrar y agrupar")
        guide_buttons.addWidget(btn_pick_guides, 0, 0)
        guide_buttons.addWidget(btn_clear_guides, 0, 1)
        guide_buttons.addWidget(btn_rename_guides, 1, 0, 1, 2)

        guide_note = QtWidgets.QLabel(
            "Use una o mas polilineas/wires del plano de trabajo. Solo se aplican al alimentador tablero -> ramal."
        )
        guide_note.setWordWrap(True)
        guide_note.setStyleSheet("color:#4b5563;")

        lay_guides.addWidget(list_guides)
        lay_guides.addLayout(guide_buttons)
        lay_guides.addWidget(guide_note)

        grp_circuits = QtWidgets.QGroupBox("Orden manual de circuitos")
        lay_circuits = QtWidgets.QVBoxLayout(grp_circuits)
        chk_manual_circuits = QtWidgets.QCheckBox("Usar orden manual")
        chk_manual_circuits.setChecked(bool(cfg.get("manual_circuit_order_enabled", False)))
        list_circuits = QtWidgets.QListWidget()
        list_circuits.setMinimumHeight(120)
        list_circuits.setDragDropMode(QtWidgets.QAbstractItemView.InternalMove)
        list_circuits.setDefaultDropAction(QtCore.Qt.MoveAction if QtCore else list_circuits.defaultDropAction())
        list_circuits.setSelectionMode(QtWidgets.QAbstractItemView.SingleSelection)
        self._set_circuit_order(list_circuits, self.circuit_items, cfg.get("manual_circuit_order", []))

        circuit_buttons = QtWidgets.QGridLayout()
        btn_refresh_circuits = QtWidgets.QPushButton("Actualizar")
        btn_circuit_up = QtWidgets.QPushButton("Subir")
        btn_circuit_down = QtWidgets.QPushButton("Bajar")
        btn_clear_circuits = QtWidgets.QPushButton("Automatico")
        circuit_buttons.addWidget(btn_refresh_circuits, 0, 0)
        circuit_buttons.addWidget(btn_clear_circuits, 0, 1)
        circuit_buttons.addWidget(btn_circuit_up, 1, 0)
        circuit_buttons.addWidget(btn_circuit_down, 1, 1)

        note_circuits = QtWidgets.QLabel(
            "Arrastre, suba o baje circuitos. Si define un orden, se usa para repartir alimentadores en el tablero."
        )
        note_circuits.setWordWrap(True)
        note_circuits.setStyleSheet("color:#4b5563;")
        lay_circuits.addWidget(chk_manual_circuits)
        lay_circuits.addWidget(list_circuits)
        lay_circuits.addLayout(circuit_buttons)
        lay_circuits.addWidget(note_circuits)

        grp_sections = QtWidgets.QGroupBox("Orden de secciones / guias")
        lay_sections = QtWidgets.QVBoxLayout(grp_sections)
        chk_manual_guides = QtWidgets.QCheckBox("Usar orden manual de secciones")
        chk_manual_guides.setChecked(bool(cfg.get("manual_guide_order_enabled", False)))
        list_sections = QtWidgets.QListWidget()
        list_sections.setMinimumHeight(110)
        list_sections.setDragDropMode(QtWidgets.QAbstractItemView.InternalMove)
        list_sections.setDefaultDropAction(QtCore.Qt.MoveAction if QtCore else list_sections.defaultDropAction())
        list_sections.setSelectionMode(QtWidgets.QAbstractItemView.SingleSelection)
        self._set_section_order(list_sections, list(cfg.get("guide_names", []) or []) + ["AUTO"], cfg.get("manual_guide_order", []))
        section_buttons = QtWidgets.QGridLayout()
        btn_refresh_sections = QtWidgets.QPushButton("Actualizar secciones")
        btn_section_up = QtWidgets.QPushButton("Subir")
        btn_section_down = QtWidgets.QPushButton("Bajar")
        btn_clear_sections = QtWidgets.QPushButton("Automatico")
        section_buttons.addWidget(btn_refresh_sections, 0, 0)
        section_buttons.addWidget(btn_clear_sections, 0, 1)
        section_buttons.addWidget(btn_section_up, 1, 0)
        section_buttons.addWidget(btn_section_down, 1, 1)
        note_sections = QtWidgets.QLabel(
            "Cada guia forma una seccion de salida del tablero. AUTO agrupa los circuitos sin guia."
        )
        note_sections.setWordWrap(True)
        note_sections.setStyleSheet("color:#4b5563;")
        lay_sections.addWidget(chk_manual_guides)
        lay_sections.addWidget(list_sections)
        lay_sections.addLayout(section_buttons)
        lay_sections.addWidget(note_sections)

        grp_section_circuits = QtWidgets.QGroupBox("Circuitos por seccion")
        lay_section_circuits = QtWidgets.QVBoxLayout(grp_section_circuits)
        chk_manual_section_circuits = QtWidgets.QCheckBox("Usar orden manual de circuitos por seccion")
        chk_manual_section_circuits.setChecked(bool(cfg.get("manual_section_circuit_order_enabled", False)))
        cmb_section_filter = QtWidgets.QComboBox()
        cmb_section_target = QtWidgets.QComboBox()
        list_section_circuits = QtWidgets.QListWidget()
        list_section_circuits.setMinimumHeight(130)
        list_section_circuits.setDragDropMode(QtWidgets.QAbstractItemView.InternalMove)
        list_section_circuits.setDefaultDropAction(QtCore.Qt.MoveAction if QtCore else list_section_circuits.defaultDropAction())
        list_section_circuits.setSelectionMode(QtWidgets.QAbstractItemView.SingleSelection)
        section_circuit_buttons = QtWidgets.QGridLayout()
        btn_refresh_section_circuits = QtWidgets.QPushButton("Actualizar circuitos")
        btn_section_circuit_up = QtWidgets.QPushButton("Subir")
        btn_section_circuit_down = QtWidgets.QPushButton("Bajar")
        btn_clear_section_circuits = QtWidgets.QPushButton("Automatico")
        section_circuit_buttons.addWidget(btn_refresh_section_circuits, 0, 0)
        section_circuit_buttons.addWidget(btn_clear_section_circuits, 0, 1)
        section_circuit_buttons.addWidget(btn_section_circuit_up, 1, 0)
        section_circuit_buttons.addWidget(btn_section_circuit_down, 1, 1)
        row_move_section = QtWidgets.QHBoxLayout()
        row_move_section.addWidget(cmb_section_target, 1)
        btn_move_section = QtWidgets.QPushButton("Mover a seccion")
        btn_reset_section = QtWidgets.QPushButton("Volver a auto")
        row_move_section.addWidget(btn_move_section)
        row_move_section.addWidget(btn_reset_section)
        note_section_circuits = QtWidgets.QLabel(
            "Seleccione una seccion para ordenar solo los circuitos que salen por esa guia o por AUTO."
        )
        note_section_circuits.setWordWrap(True)
        note_section_circuits.setStyleSheet("color:#4b5563;")
        lay_section_circuits.addWidget(chk_manual_section_circuits)
        lay_section_circuits.addWidget(cmb_section_filter)
        lay_section_circuits.addWidget(list_section_circuits)
        lay_section_circuits.addLayout(section_circuit_buttons)
        lay_section_circuits.addLayout(row_move_section)
        lay_section_circuits.addWidget(note_section_circuits)

        section_order_state = {
            key: list(vals)
            for key, vals in dict(cfg.get("manual_section_circuit_order_map", {}) or {}).items()
            if _safe_text(key).strip()
        }
        section_override_state = {
            _safe_text(k).strip(): _safe_text(v).strip()
            for k, v in dict(cfg.get("manual_section_override_map", {}) or {}).items()
            if _safe_text(k).strip() and _safe_text(v).strip()
        }
        section_preview = {"map": {}, "keys": []}
        active_section_state = {"key": "AUTO"}

        def _save_active_section_order():
            sec_key = _safe_text(active_section_state.get("key", "")).strip()
            if not sec_key:
                return
            section_order_state[sec_key] = self._selected_section_circuit_ids(list_section_circuits)

        def _load_active_section_order():
            sec_key = _safe_text(cmb_section_filter.currentData()).strip() or "AUTO"
            active_section_state["key"] = sec_key
            items = list(section_preview["map"].get(sec_key, []) or [])
            self._set_section_circuit_order(
                list_section_circuits,
                items,
                section_order_state.get(sec_key, []),
            )

        def _refresh_sections_and_circuits():
            _save_active_section_order()
            section_keys, section_map = self._preview_section_circuit_items(
                anchor_name=_safe_text(cmb_anchor.currentData()).strip(),
                anchor_face=_safe_text(cmb_anchor_face.currentText() or "Auto"),
                anchor_faces=self._selected_anchor_face_names(list_anchor_faces),
                guide_names=self._selected_guide_names(list_guides),
                include_apagadores=bool(cfg.get("include_apagadores", True)),
                section_override_map=section_override_state,
            )
            section_preview["map"] = dict(section_map or {})
            section_preview["keys"] = list(section_keys or [])
            self._set_section_order(
                list_sections,
                section_preview["keys"],
                self._selected_section_keys(list_sections) or cfg.get("manual_guide_order", []),
            )
            self._set_section_keys_in_combo(cmb_section_filter, self._selected_section_keys(list_sections))
            self._set_section_keys_in_combo(cmb_section_target, self._selected_section_keys(list_sections))
            _load_active_section_order()

        def _move_selected_circuit_to_section(target_section=None, reset_to_auto=False):
            item = list_section_circuits.currentItem()
            gid = _safe_text(item.data(QtCore.Qt.UserRole) if (QtCore and item is not None) else (item.text() if item is not None else "")).strip()
            if not gid:
                _warn("Seleccione un circuito en la lista de la seccion actual.")
                return
            _save_active_section_order()
            for sec_key in list(section_order_state.keys()):
                section_order_state[sec_key] = [x for x in (section_order_state.get(sec_key, []) or []) if _safe_text(x).strip() != gid]
            if reset_to_auto:
                section_override_state.pop(gid, None)
                target_key = "AUTO"
            else:
                target_key = _safe_text(target_section or cmb_section_target.currentData()).strip() or "AUTO"
                section_override_state[gid] = target_key
            target_list = list(section_order_state.get(target_key, []) or [])
            if gid not in target_list:
                target_list.append(gid)
            section_order_state[target_key] = target_list
            _refresh_sections_and_circuits()
            idx = cmb_section_filter.findData(target_key)
            if idx >= 0:
                cmb_section_filter.setCurrentIndex(idx)
            _load_active_section_order()

        _refresh_sections_and_circuits()

        info_scope = QtWidgets.QLabel(
            "Alcance: si selecciona tomas, apagadores o grupos de circuito antes de abrir la macro, "
            "se procesaran esos circuitos. Si no hay seleccion util, se procesara todo el arbol."
        )
        info_scope.setWordWrap(True)
        info_scope.setStyleSheet("color:#4b5563;")

        lay_scope.addWidget(grp_scope)
        lay_scope.addWidget(grp_anchor_faces)
        lay_scope.addWidget(sel_box)
        lay_scope.addWidget(grp_guides)
        lay_scope.addWidget(info_scope)
        lay_scope.addStretch(1)

        tab_route = QtWidgets.QWidget()
        lay_route = QtWidgets.QVBoxLayout(tab_route)

        grp_conduit = QtWidgets.QGroupBox("Canalizacion")
        form_conduit = QtWidgets.QFormLayout(grp_conduit)
        cmb_type = QtWidgets.QComboBox()
        cmb_type.addItems(["EMT", "PVC"])
        idx = max(0, cmb_type.findText(_safe_text(cfg.get("conduit_type", DEFAULT_CONDUIT)).upper()))
        cmb_type.setCurrentIndex(idx)

        sp_diam = QtWidgets.QDoubleSpinBox()
        sp_diam.setRange(1.0, 200.0)
        sp_diam.setDecimals(1)
        sp_diam.setSuffix(" mm")
        sp_diam.setValue(float(cfg.get("diameter", DEFAULT_DIAMETER)))

        sp_route_z = QtWidgets.QDoubleSpinBox()
        sp_route_z.setRange(-5000.0, 20000.0)
        sp_route_z.setDecimals(1)
        sp_route_z.setSuffix(" mm")
        sp_route_z.setValue(float(cfg.get("route_z", DEFAULT_ROUTE_Z)))

        sp_bend = QtWidgets.QDoubleSpinBox()
        sp_bend.setRange(10.0, 1000.0)
        sp_bend.setDecimals(1)
        sp_bend.setSuffix(" mm")
        sp_bend.setValue(float(cfg.get("bend_radius", DEFAULT_BEND_RADIUS)))

        cmb_axis = QtWidgets.QComboBox()
        cmb_axis.addItems(["Horizontal", "Vertical"])
        axis_txt = _safe_text(cfg.get("feeder_axis", DEFAULT_FEEDER_AXIS)).strip() or DEFAULT_FEEDER_AXIS
        axis_idx = max(0, cmb_axis.findText(axis_txt))
        cmb_axis.setCurrentIndex(axis_idx)

        sp_margin = QtWidgets.QDoubleSpinBox()
        sp_margin.setRange(0.0, 5000.0)
        sp_margin.setDecimals(1)
        sp_margin.setSuffix(" mm")
        sp_margin.setValue(float(cfg.get("wall_margin", DEFAULT_WALL_OFFSET)))
        sp_margin.setToolTip("0 mantiene la ruta exactamente sobre el perimetro definido por cajas y tablero.")

        sp_sep = QtWidgets.QDoubleSpinBox()
        sp_sep.setRange(0.0, 5000.0)
        sp_sep.setDecimals(1)
        sp_sep.setSuffix(" mm")
        sp_sep.setValue(float(cfg.get("circuit_separation", DEFAULT_CIRCUIT_SEPARATION)))

        form_conduit.addRow("Tipo:", cmb_type)
        form_conduit.addRow("Diametro:", sp_diam)
        form_conduit.addRow("Nivel ruta:", sp_route_z)
        form_conduit.addRow("Radio curvatura:", sp_bend)
        form_conduit.addRow("Organizar alimentadores:", cmb_axis)
        form_conduit.addRow("Offset extra al perimetro:", sp_margin)
        form_conduit.addRow("Separacion circuitos:", sp_sep)

        note_route = QtWidgets.QLabel(
            "Regla de proyecto: el perimetro ya lo definen las octogonales sobre el muro. "
            "Use offset extra solo si quiere despegar intencionalmente la ruta."
        )
        note_route.setWordWrap(True)
        note_route.setStyleSheet("color:#4b5563;")

        lay_route.addWidget(grp_conduit)
        lay_route.addWidget(note_route)
        lay_route.addStretch(1)

        tab_rules = QtWidgets.QWidget()
        lay_rules_tab = QtWidgets.QVBoxLayout(tab_rules)
        grp_rules = QtWidgets.QGroupBox("Reglas")
        lay_rules = QtWidgets.QVBoxLayout(grp_rules)

        tab_circuits = QtWidgets.QWidget()
        lay_circuits_tab = QtWidgets.QVBoxLayout(tab_circuits)
        circuits_toolbox = QtWidgets.QToolBox()
        circuits_toolbox.setSizePolicy(QtWidgets.QSizePolicy.Expanding, QtWidgets.QSizePolicy.Preferred)
        page_sections = QtWidgets.QWidget()
        lay_page_sections = QtWidgets.QVBoxLayout(page_sections)
        lay_page_sections.setContentsMargins(0, 0, 0, 0)
        lay_page_sections.addWidget(grp_sections)
        lay_page_sections.addStretch(1)
        page_section_circuits = QtWidgets.QWidget()
        lay_page_section_circuits = QtWidgets.QVBoxLayout(page_section_circuits)
        lay_page_section_circuits.setContentsMargins(0, 0, 0, 0)
        lay_page_section_circuits.addWidget(grp_section_circuits)
        lay_page_section_circuits.addStretch(1)
        circuits_toolbox.addItem(page_sections, "Secciones / guias")
        circuits_toolbox.addItem(page_section_circuits, "Circuitos por seccion")
        circuits_toolbox.setCurrentIndex(1)
        lay_circuits_tab.addWidget(circuits_toolbox)
        lay_circuits_tab.addStretch(1)

        chk_apa = QtWidgets.QCheckBox("Incluir apagadores")
        chk_apa.setChecked(bool(cfg.get("include_apagadores", True)))
        chk_missing = QtWidgets.QCheckBox("Si falta caja, conectar al dispositivo mas cercano")
        chk_missing.setChecked(bool(cfg.get("fallback_missing_box", True)))
        chk_same_level = QtWidgets.QCheckBox("Conexion directa dispositivo-dispositivo solo si estan a la misma cota")
        chk_same_level.setChecked(bool(cfg.get("direct_same_level_only", True)))
        sp_level_tol = QtWidgets.QDoubleSpinBox()
        sp_level_tol.setRange(0.0, 500.0)
        sp_level_tol.setDecimals(1)
        sp_level_tol.setSuffix(" mm")
        sp_level_tol.setValue(float(cfg.get("device_level_tolerance", DEFAULT_DEVICE_LEVEL_TOLERANCE)))
        row_level_tol = QtWidgets.QWidget()
        row_level_tol_lay = QtWidgets.QHBoxLayout(row_level_tol)
        row_level_tol_lay.setContentsMargins(18, 0, 0, 0)
        row_level_tol_lay.addWidget(QtWidgets.QLabel("Tolerancia de cota:"))
        row_level_tol_lay.addWidget(sp_level_tol)
        row_level_tol_lay.addStretch(1)
        chk_ortho = QtWidgets.QCheckBox("Ruta ortogonal (X-Y-Z)")
        chk_ortho.setChecked(bool(cfg.get("orthogonal_route", True)))
        chk_perim = QtWidgets.QCheckBox("Ruta por perimetro del circuito")
        chk_perim.setChecked(bool(cfg.get("route_by_perimeter", True)))
        chk_ports = QtWidgets.QCheckBox("Reservar puertos para evitar repetir agujero")
        chk_ports.setChecked(bool(cfg.get("reserve_ports", True)))
        chk_existing = QtWidgets.QCheckBox("Omitir conexiones ya creadas por esta macro")
        chk_existing.setChecked(bool(cfg.get("skip_existing", True)))
        chk_debug = QtWidgets.QCheckBox("Registrar debug detallado en archivo")
        chk_debug.setChecked(bool(cfg.get("debug_enabled", True)))

        lay_rules.addWidget(chk_apa)
        lay_rules.addWidget(chk_missing)
        lay_rules.addWidget(chk_same_level)
        lay_rules.addWidget(row_level_tol)
        lay_rules.addWidget(chk_ortho)
        lay_rules.addWidget(chk_perim)
        lay_rules.addWidget(chk_ports)
        lay_rules.addWidget(chk_existing)

        grp_debug = QtWidgets.QGroupBox("Debug")
        lay_debug = QtWidgets.QVBoxLayout(grp_debug)
        lbl_debug_path = QtWidgets.QLabel(f"Archivo: {_debug_log_path()}")
        lbl_debug_path.setWordWrap(True)
        lbl_debug_path.setStyleSheet("color:#4b5563;")
        btn_open_log = QtWidgets.QPushButton("Abrir log")
        lay_debug.addWidget(chk_debug)
        lay_debug.addWidget(lbl_debug_path)
        lay_debug.addWidget(btn_open_log)

        note_rules = QtWidgets.QLabel(
            "Las octogonales se manejan con cardinales coherentes Norte/Sur/Este/Oeste para que la tuberia entre perpendicularmente al lado correspondiente."
        )
        note_rules.setWordWrap(True)
        note_rules.setStyleSheet("color:#4b5563;")

        lay_rules_tab.addWidget(grp_rules)
        lay_rules_tab.addWidget(grp_debug)
        lay_rules_tab.addWidget(note_rules)
        lay_rules_tab.addStretch(1)

        tabs.addTab(tab_scope, "Alcance")
        tabs.addTab(tab_route, "Ruta")
        tabs.addTab(tab_circuits, "Circuitos")
        tabs.addTab(tab_rules, "Reglas")

        buttons = QtWidgets.QDialogButtonBox(QtWidgets.QDialogButtonBox.Ok | QtWidgets.QDialogButtonBox.Cancel)
        btn_apply_refresh = buttons.addButton("Actualizar alimentadores", QtWidgets.QDialogButtonBox.ActionRole)
        btn_pick_anchor.clicked.connect(lambda: (self._assign_anchor_from_selection(cmb_anchor), _refresh_sections_and_circuits()))
        btn_pick_anchor_faces.clicked.connect(lambda: (self._assign_anchor_faces_from_selection(cmb_anchor, cmb_anchor_face, list_anchor_faces, txt_anchor_face, lbl_anchor_faces_state), _refresh_sections_and_circuits()))
        btn_clear_anchor_faces.clicked.connect(lambda: (self._clear_anchor_faces(cmb_anchor_face, list_anchor_faces, txt_anchor_face, lbl_anchor_faces_state), _refresh_sections_and_circuits()))
        btn_refresh.clicked.connect(lambda: self._refresh_anchor_list(cmb_anchor))
        btn_pick_guides.clicked.connect(lambda: (self._assign_guides_from_selection(list_guides), _refresh_sections_and_circuits()))
        btn_clear_guides.clicked.connect(lambda: (self._clear_guides(list_guides), _refresh_sections_and_circuits()))
        btn_rename_guides.clicked.connect(lambda: (self._rename_and_group_guides(list_guides), _refresh_sections_and_circuits()))
        btn_refresh_circuits.clicked.connect(lambda: self._refresh_circuit_order(list_circuits))
        btn_circuit_up.clicked.connect(lambda: (chk_manual_circuits.setChecked(True), self._move_circuit_order(list_circuits, -1)))
        btn_circuit_down.clicked.connect(lambda: (chk_manual_circuits.setChecked(True), self._move_circuit_order(list_circuits, 1)))
        btn_clear_circuits.clicked.connect(lambda: (chk_manual_circuits.setChecked(False), self._clear_circuit_order(list_circuits)))
        btn_refresh_sections.clicked.connect(_refresh_sections_and_circuits)
        btn_section_up.clicked.connect(lambda: (chk_manual_guides.setChecked(True), self._move_circuit_order(list_sections, -1), self._set_section_keys_in_combo(cmb_section_filter, self._selected_section_keys(list_sections)), self._set_section_keys_in_combo(cmb_section_target, self._selected_section_keys(list_sections))))
        btn_section_down.clicked.connect(lambda: (chk_manual_guides.setChecked(True), self._move_circuit_order(list_sections, 1), self._set_section_keys_in_combo(cmb_section_filter, self._selected_section_keys(list_sections)), self._set_section_keys_in_combo(cmb_section_target, self._selected_section_keys(list_sections))))
        btn_clear_sections.clicked.connect(lambda: (chk_manual_guides.setChecked(False), self._set_section_order(list_sections, section_preview.get("keys", []), []), self._set_section_keys_in_combo(cmb_section_filter, self._selected_section_keys(list_sections)), self._set_section_keys_in_combo(cmb_section_target, self._selected_section_keys(list_sections))))
        cmb_section_filter.currentIndexChanged.connect(lambda _idx: (_save_active_section_order(), _load_active_section_order()))
        btn_refresh_section_circuits.clicked.connect(_refresh_sections_and_circuits)
        btn_section_circuit_up.clicked.connect(lambda: (chk_manual_section_circuits.setChecked(True), self._move_circuit_order(list_section_circuits, -1), _save_active_section_order()))
        btn_section_circuit_down.clicked.connect(lambda: (chk_manual_section_circuits.setChecked(True), self._move_circuit_order(list_section_circuits, 1), _save_active_section_order()))
        btn_clear_section_circuits.clicked.connect(lambda: (chk_manual_section_circuits.setChecked(False), section_order_state.__setitem__(_safe_text(cmb_section_filter.currentData()).strip() or "AUTO", []), _load_active_section_order()))
        btn_move_section.clicked.connect(lambda: _move_selected_circuit_to_section())
        btn_reset_section.clicked.connect(lambda: _move_selected_circuit_to_section(reset_to_auto=True))
        btn_open_log.clicked.connect(_open_debug_log)
        if QtCore is not None:
            try:
                list_sections.model().rowsMoved.connect(lambda *_args: (chk_manual_guides.setChecked(True), self._set_section_keys_in_combo(cmb_section_filter, self._selected_section_keys(list_sections)), self._set_section_keys_in_combo(cmb_section_target, self._selected_section_keys(list_sections))))
            except Exception:
                pass
            try:
                list_section_circuits.model().rowsMoved.connect(lambda *_args: (chk_manual_section_circuits.setChecked(True), _save_active_section_order()))
            except Exception:
                pass

        lay.addWidget(hdr)
        lay.addWidget(lbl_selection)
        lay.addWidget(tabs)
        lay.addWidget(buttons)

        if QtCore is not None:
            loop = QtCore.QEventLoop()
            state = {"accepted": False, "refresh_routes": False}

            def _accept_and_close():
                state["accepted"] = True
                state["refresh_routes"] = False
                if dock is not None:
                    dock.close()
                else:
                    dlg.accept()

            def _refresh_and_close():
                state["accepted"] = True
                state["refresh_routes"] = True
                if dock is not None:
                    dock.close()
                else:
                    dlg.accept()

            def _reject_and_close():
                state["accepted"] = False
                state["refresh_routes"] = False
                if dock is not None:
                    dock.close()
                else:
                    dlg.reject()

            buttons.accepted.connect(_accept_and_close)
            buttons.rejected.connect(_reject_and_close)
            btn_apply_refresh.clicked.connect(_refresh_and_close)

            if dock is not None:
                try:
                    dock.visibilityChanged.connect(lambda visible: loop.quit() if not visible else None)
                except Exception:
                    pass
                dock.show()
                try:
                    dock.raise_()
                except Exception:
                    pass
            else:
                self._move_dialog_to_side(dlg, parent)
                dlg.show()
                QtWidgets.QApplication.processEvents()
                self._move_dialog_to_side(dlg, parent)
                QtCore.QTimer.singleShot(0, lambda: self._move_dialog_to_side(dlg, parent))
                try:
                    dlg.raise_()
                    dlg.activateWindow()
                except Exception:
                    pass
                dlg.finished.connect(loop.quit)

            loop.exec_()
            accepted = bool(state["accepted"]) if dock is not None else (dlg.result() == QtWidgets.QDialog.Accepted)
        else:
            buttons.accepted.connect(dlg.accept)
            buttons.rejected.connect(dlg.reject)
            accepted = dlg.exec_() == QtWidgets.QDialog.Accepted
        if not accepted:
            return None

        cfg["anchor_name"] = _safe_text(cmb_anchor.currentData()).strip()
        cfg["anchor_faces"] = self._selected_anchor_face_names(list_anchor_faces)
        cfg["anchor_face"] = (cfg["anchor_faces"][0] if len(cfg["anchor_faces"]) == 1 else "Auto")
        cfg["guide_names"] = self._selected_guide_names(list_guides)
        cfg["manual_circuit_order"] = self._selected_circuit_order_ids(list_circuits)
        cfg["manual_circuit_order_enabled"] = bool(chk_manual_circuits.isChecked())
        _save_active_section_order()
        cfg["manual_guide_order"] = self._selected_section_keys(list_sections)
        cfg["manual_guide_order_enabled"] = bool(chk_manual_guides.isChecked())
        cfg["manual_section_circuit_order_map"] = {
            _safe_text(k).strip(): list(v)
            for k, v in dict(section_order_state or {}).items()
            if _safe_text(k).strip()
        }
        cfg["manual_section_circuit_order_enabled"] = bool(chk_manual_section_circuits.isChecked())
        cfg["manual_section_override_map"] = {
            _safe_text(k).strip(): _safe_text(v).strip()
            for k, v in dict(section_override_state or {}).items()
            if _safe_text(k).strip() and _safe_text(v).strip()
        }
        cfg["refresh_existing_routes"] = bool(state.get("refresh_routes", False)) if QtCore is not None else False
        cfg["conduit_type"] = _safe_text(cmb_type.currentText() or DEFAULT_CONDUIT).upper()
        cfg["diameter"] = float(sp_diam.value())
        cfg["route_z"] = float(sp_route_z.value())
        cfg["bend_radius"] = float(sp_bend.value())
        cfg["feeder_axis"] = _safe_text(cmb_axis.currentText() or DEFAULT_FEEDER_AXIS)
        cfg["wall_margin"] = float(sp_margin.value())
        cfg["circuit_separation"] = float(sp_sep.value())
        cfg["include_apagadores"] = bool(chk_apa.isChecked())
        cfg["fallback_missing_box"] = bool(chk_missing.isChecked())
        cfg["direct_same_level_only"] = bool(chk_same_level.isChecked())
        cfg["device_level_tolerance"] = float(sp_level_tol.value())
        cfg["connect_to_board"] = bool(chk_board.isChecked())
        cfg["orthogonal_route"] = bool(chk_ortho.isChecked())
        cfg["route_by_perimeter"] = bool(chk_perim.isChecked())
        cfg["reserve_ports"] = bool(chk_ports.isChecked())
        cfg["skip_existing"] = bool(chk_existing.isChecked())
        cfg["debug_enabled"] = bool(chk_debug.isChecked())
        _save_config(cfg)
        return cfg


def _is_group(obj):
    if obj is None:
        return False
    try:
        if obj.isDerivedFrom("App::DocumentObjectGroup"):
            return True
    except Exception:
        pass
    try:
        if obj.isDerivedFrom("App::Part"):
            return True
    except Exception:
        pass
    return hasattr(obj, "Group")


def _parent_group(obj):
    if obj is None:
        return None
    if hasattr(obj, "getParentGroup"):
        try:
            pg = obj.getParentGroup()
            if pg is not None:
                return pg
        except Exception:
            pass
    for parent in (getattr(obj, "InList", []) or []):
        if _is_group(parent):
            return parent
    return None


def _group_chain_topdown(obj):
    chain = []
    seen = set()
    cur = obj
    while True:
        pg = _parent_group(cur)
        if pg is None:
            break
        name = _safe_text(getattr(pg, "Name", ""))
        if not name or name in seen:
            break
        seen.add(name)
        chain.append(pg)
        cur = pg
    chain.reverse()
    return chain


def _group_id(group_obj):
    if group_obj is None:
        return ""
    return _safe_text(getattr(group_obj, "Name", "")) or _safe_text(getattr(group_obj, "Label", ""))


def _is_conexiones_group(group_obj):
    txt = f"{_safe_text(getattr(group_obj, 'Name', ''))} {_safe_text(getattr(group_obj, 'Label', ''))}".lower()
    return ("conexion" in txt) or txt.startswith("conexiones")


def _natural_key(text):
    s = _safe_text(text).strip().lower()
    parts = re.split(r"(\d+)", s)
    out = []
    for p in parts:
        if p.isdigit():
            out.append(int(p))
        else:
            out.append(p)
    return tuple(out)


def _is_circuit_group(group_obj):
    txt = f"{_safe_text(getattr(group_obj, 'Name', ''))} {_safe_text(getattr(group_obj, 'Label', ''))}".lower()
    if ("circuito" in txt) or ("circuit" in txt):
        return True
    return bool(re.search(r"\btp[\s\-_]*\d+", txt))


def _iter_non_group_descendants(root_group, skip_conexiones=True):
    if root_group is None:
        return
    stack = list((getattr(root_group, "Group", []) or []))
    while stack:
        obj = stack.pop(0)
        if _is_group(obj):
            if skip_conexiones and _is_conexiones_group(obj):
                continue
            stack[0:0] = list(getattr(obj, "Group", []) or [])
            continue
        yield obj


def _selection_objects():
    if not GUI_UP:
        return []
    try:
        return list(Gui.Selection.getSelection() or [])
    except Exception:
        return []


def _selection_ex():
    if not GUI_UP:
        return []
    try:
        return list(Gui.Selection.getSelectionEx() or [])
    except Exception:
        return []


def _find_object_by_name(doc, name):
    key = _safe_text(name).strip()
    if not key or doc is None:
        return None
    try:
        return doc.getObject(key)
    except Exception:
        return None


def _objects_by_names(doc, names):
    out = []
    seen = set()
    for name in (names or []):
        obj = _find_object_by_name(doc, name)
        oname = _safe_text(getattr(obj, "Name", "")).strip() if obj is not None else ""
        if obj is None or not oname or oname in seen:
            continue
        seen.add(oname)
        out.append(obj)
    return out


def _ancestor_circuit_groups(obj):
    out = []
    seen = set()
    for grp in _group_chain_topdown(obj):
        gid = _group_id(grp)
        if not gid or gid in seen:
            continue
        seen.add(gid)
        if _is_circuit_group(grp):
            out.append(grp)
    return out


def _selection_context(doc):
    sel = _selection_objects()
    groups = []
    seen_groups = set()
    anchor = None

    for obj in sel:
        if obj is None:
            continue
        if anchor is None and not _is_group(obj) and _fallback_component_type(obj) == "Tablero":
            anchor = obj
        if _is_group(obj):
            gid = _group_id(obj)
            if gid and gid not in seen_groups:
                seen_groups.add(gid)
                groups.append(obj)
            continue
        for grp in _ancestor_circuit_groups(obj):
            gid = _group_id(grp)
            if gid and gid not in seen_groups:
                seen_groups.add(gid)
                groups.append(grp)

    selection_anchor = anchor
    pref_anchor = _find_object_by_name(doc, _pref_get_str("anchor_name", ""))
    if anchor is None and pref_anchor is not None:
        anchor = pref_anchor

    return {
        "selection": sel,
        "groups": groups,
        "selection_anchor": selection_anchor,
        "anchor": anchor,
    }


def _find_group_by_name_or_label(doc, wanted):
    w = _safe_text(wanted).strip().lower()
    if not w:
        return None
    for obj in (doc.Objects or []):
        if not _is_group(obj):
            continue
        n = _safe_text(getattr(obj, "Name", "")).strip().lower()
        l = _safe_text(getattr(obj, "Label", "")).strip().lower()
        if n == w or l == w:
            return obj
    return None


def _find_child_group_by_label(parent, label):
    want = _safe_text(label).strip().lower()
    if not want or parent is None:
        return None
    for child in (getattr(parent, "Group", []) or []):
        if not _is_group(child):
            continue
        n = _safe_text(getattr(child, "Name", "")).strip().lower()
        l = _safe_text(getattr(child, "Label", "")).strip().lower()
        if n == want or l == want:
            return child
    return None


def _ensure_child_group(doc, parent, label, prefix="Group"):
    existing = _find_child_group_by_label(parent, label)
    if existing is not None:
        return existing

    token = _safe_name_token(label, "Grupo")
    base = f"{prefix}_{_safe_name_token(getattr(parent, 'Name', 'Root'), 'Root')}_{token}"
    name = base
    i = 1
    while doc.getObject(name) is not None:
        name = f"{base}_{i:02d}"
        i += 1
    grp = doc.addObject("App::DocumentObjectGroup", name)
    try:
        grp.Label = _safe_text(label) or token
    except Exception:
        pass
    try:
        parent.addObject(grp)
    except Exception:
        pass
    return grp


def _candidate_circuit_groups(doc, selected_groups):
    out = []
    seen = set()

    def add_group(g):
        if g is None or not _is_group(g):
            return
        gid = _group_id(g)
        if not gid or gid in seen:
            return
        seen.add(gid)
        out.append(g)

    if selected_groups:
        for g in selected_groups:
            if _is_circuit_group(g):
                add_group(g)
            else:
                for child in (getattr(g, "Group", []) or []):
                    if _is_group(child) and _is_circuit_group(child):
                        add_group(child)
        if out:
            return out

    roots = [
        _find_group_by_name_or_label(doc, "Tomacorrientes"),
        _find_group_by_name_or_label(doc, "Apagadores"),
    ]
    for root in roots:
        if root is None:
            continue
        children = [c for c in (getattr(root, "Group", []) or []) if _is_group(c)]
        for g in children:
            if _is_circuit_group(g):
                add_group(g)
        if not children:
            add_group(root)
    return out


def _manual_circuit_rank_map(cfg):
    if not bool(cfg.get("manual_circuit_order_enabled", False)):
        return {}
    out = {}
    for idx, gid in enumerate(cfg.get("manual_circuit_order", []) or []):
        key = _safe_text(gid).strip()
        if key and key not in out:
            out[key] = int(idx)
    return out


def _sort_circuit_groups_manual(circuit_groups, cfg):
    rank_map = _manual_circuit_rank_map(cfg)
    if not rank_map:
        return sorted(circuit_groups, key=lambda g: _natural_key(_circuit_id_for_group(g)))
    return sorted(
        circuit_groups,
        key=lambda g: (
            int(rank_map.get(_group_id(g), 10 ** 9)),
            _natural_key(_circuit_id_for_group(g)),
        ),
    )


def _import_component_classifier():
    try:
        here = Path(__file__).resolve().parent
    except Exception:
        here = None
    cands = []
    if here is not None:
        cands.append(str(here))
    if _safe_text(__file__):
        cands.append(os.path.dirname(__file__))
    for p in cands:
        if p and p not in sys.path:
            sys.path.insert(0, p)
    try:
        mod = importlib.import_module("component_classifier")
        fn = getattr(mod, "get_component_type", None)
        if callable(fn):
            return fn
    except Exception:
        pass
    return None


def _import_conexiones_grouping():
    try:
        here = Path(__file__).resolve().parent
    except Exception:
        here = None
    cands = []
    if here is not None:
        cands.append(str(here))
    if _safe_text(__file__):
        cands.append(os.path.dirname(__file__))
    for p in cands:
        if p and p not in sys.path:
            sys.path.insert(0, p)
    mod = importlib.import_module("conexiones_grouping")
    mod = importlib.reload(mod)
    fn = getattr(mod, "ensure_conexiones_group", None)
    if not callable(fn):
        raise RuntimeError("No se encontro ensure_conexiones_group en conexiones_grouping.py")
    return fn


def _fallback_component_type(obj):
    for attr in ("Tipo", "TipoLogico", "Categoria"):
        try:
            t = _safe_text(getattr(obj, attr, "")).strip().lower()
            if "toma" in t:
                return "Toma"
            if ("apagador" in t) or ("switch" in t) or ("interruptor" in t):
                return "Apagador"
            if "tablero" in t:
                return "Tablero"
        except Exception:
            pass
    txt = f"{_safe_text(getattr(obj, 'Label', ''))} {_safe_text(getattr(obj, 'Name', ''))}".lower()
    if "toma" in txt:
        return "Toma"
    if ("apagador" in txt) or ("switch" in txt) or ("interruptor" in txt):
        return "Apagador"
    if "tablero" in txt:
        return "Tablero"
    return ""


def _is_octagon_box(obj):
    if obj is None or _is_group(obj):
        return False
    try:
        t = _safe_text(getattr(obj, "Tipo", "")).strip()
        if t == "EMT_Octagon_Box":
            return True
    except Exception:
        pass
    txt = f"{_safe_text(getattr(obj, 'Label', ''))} {_safe_text(getattr(obj, 'Name', ''))}".lower()
    if ("caja emt octogonal" in txt) or ("emt_octagon_box" in txt):
        return True
    if hasattr(obj, "CajaOrigenKey") and hasattr(obj, "PuertosJSON"):
        return True
    return False


def _source_key(obj):
    for attr in ("UUID",):
        try:
            txt = _safe_text(getattr(obj, attr, "")).strip()
            if txt:
                return f"UUID:{txt}"
        except Exception:
            pass
    return f"NAME:{_safe_text(getattr(obj, 'Name', ''))}"


def _center_from_shapes(shapes):
    xmin = ymin = zmin = None
    xmax = ymax = zmax = None
    used = False
    for shp in (shapes or []):
        try:
            bb = shp.BoundBox
        except Exception:
            continue
        if bb is None:
            continue
        if xmin is None:
            xmin, ymin, zmin = bb.XMin, bb.YMin, bb.ZMin
            xmax, ymax, zmax = bb.XMax, bb.YMax, bb.ZMax
            used = True
        else:
            xmin = min(xmin, bb.XMin)
            ymin = min(ymin, bb.YMin)
            zmin = min(zmin, bb.ZMin)
            xmax = max(xmax, bb.XMax)
            ymax = max(ymax, bb.YMax)
            zmax = max(zmax, bb.ZMax)
            used = True
    if not used:
        return None
    return _vec(0.5 * (xmin + xmax), 0.5 * (ymin + ymax), 0.5 * (zmin + zmax))


def _shape_center_pref3d(obj):
    try:
        shape = getattr(obj, "Shape", None)
    except Exception:
        shape = None
    if shape is None:
        return None
    try:
        if shape.isNull():
            return None
    except Exception:
        pass

    try:
        solids = list(getattr(shape, "Solids", []) or [])
    except Exception:
        solids = []
    if solids:
        c = _center_from_shapes(solids)
        if c is not None:
            return c

    try:
        faces3d = []
        for fc in (getattr(shape, "Faces", []) or []):
            try:
                if fc.BoundBox.ZLength > 1e-3:
                    faces3d.append(fc)
            except Exception:
                pass
        if faces3d:
            c = _center_from_shapes(faces3d)
            if c is not None:
                return c
    except Exception:
        pass

    try:
        bb = shape.BoundBox
        return _vec(0.5 * (bb.XMin + bb.XMax), 0.5 * (bb.YMin + bb.YMax), 0.5 * (bb.ZMin + bb.ZMax))
    except Exception:
        return None


def _source_rotation(obj):
    try:
        rot = obj.Placement.Rotation
    except Exception:
        rot = App.Rotation()

    giro = _to_float(getattr(obj, "Giro", 0.0), 0.0)
    if abs(giro) > 1e-9:
        extra = App.Rotation(_vec(0.0, 0.0, 1.0), giro)
        try:
            rot = rot.multiply(extra)
        except Exception:
            try:
                rot = rot * extra
            except Exception:
                pass
    return rot


def _anchor_point(obj):
    if obj is None:
        return _vec(0.0, 0.0, 0.0)

    if _is_group(obj):
        pts = []
        for child in _iter_non_group_descendants(obj, skip_conexiones=True):
            pts.append(_anchor_point(child))
            if len(pts) >= 250:
                break
        if pts:
            sx = sum(p.x for p in pts)
            sy = sum(p.y for p in pts)
            sz = sum(p.z for p in pts)
            n = float(len(pts))
            return _vec(sx / n, sy / n, sz / n)
        return _vec(0.0, 0.0, 0.0)

    c = _shape_center_pref3d(obj)
    if c is not None:
        return c

    try:
        base = obj.Placement.Base
    except Exception:
        base = _vec(0.0, 0.0, 0.0)
    offx = _to_float(getattr(obj, "OffsetX", 0.0), 0.0)
    offy = _to_float(getattr(obj, "OffsetY", 0.0), 0.0)
    altura = _to_float(getattr(obj, "AlturaRel", 0.0), 0.0)
    local = _vec(offx, offy, altura)
    return base + _source_rotation(obj).multVec(local)


def _ports_from_json(raw):
    try:
        data = json.loads(_safe_text(raw))
        if isinstance(data, list):
            return data
    except Exception:
        pass
    return []


def _rename_octagon_ports_world(obj, ports):
    center = _anchor_point(obj)
    side = []
    bottom = None
    for p in (ports or []):
        name = _safe_text(p.get("name", "")).strip()
        if name == "Bottom":
            bottom = dict(p)
            continue
        wd = _normalize(_vec(p["dir"].x, p["dir"].y, 0.0)) if _vlen(p.get("dir", _vec(0.0, 0.0, 0.0))) > EPS else _vec(0.0, 0.0, 0.0)
        if _vlen(wd) <= EPS:
            wd = _normalize(_vec(float(p["point"].x) - float(center.x), float(p["point"].y) - float(center.y), 0.0))
        angle = _angle_deg_xy(wd) if _vlen(wd) > EPS else 0.0
        side.append((dict(p), angle))

    # Filtrar puertos internos: solo conservar puertos cercanos al perimetro
    # de la caja para evitar rutas que nacen dentro del volumen.
    if side and bool(globals().get("RAMAL_LUZ_PATCH_ACTIVE", False)):
        with_radius = []
        for p, ang in side:
            try:
                r = _distance_xy(p["point"], center)
            except Exception:
                r = 0.0
            with_radius.append((p, ang, float(r)))
        max_r = max((r for _p, _a, r in with_radius), default=0.0)
        if max_r > EPS:
            min_r = max(5.0, 0.55 * float(max_r))
            ring = [(p, ang) for p, ang, r in with_radius if r >= min_r]
            # Si el filtro deja demasiado poco, no romper compatibilidad.
            if len(ring) >= 4:
                side = ring

    remaining = list(side)
    assigned = {}
    for label, target in OCTAGON_PORT_TARGETS:
        if not remaining:
            break
        best = min(
            remaining,
            key=lambda item: (
                _circular_distance_deg(item[1], target),
                item[0]["point"].distanceToPoint(center),
            ),
        )
        port = dict(best[0])
        port["name"] = label
        assigned[label] = port
        remaining.remove(best)

    for label, _target in OCTAGON_PORT_TARGETS:
        if label not in assigned:
            continue
    out = []
    order = ["North", "South", "East", "West", "NorthEast", "NorthWest", "SouthEast", "SouthWest"]
    for label in order:
        port = assigned.get(label)
        if port is not None:
            out.append(port)
    if bottom is not None:
        try:
            bdir = bottom.get("dir", _vec(0.0, 0.0, 0.0))
            if _vlen(bdir) <= EPS:
                bottom["dir"] = _vec(0.0, 0.0, -1.0)
        except Exception:
            pass
        out.append(bottom)
    return out


def _world_ports(obj):
    ports = _ports_from_json(getattr(obj, "PuertosJSON", ""))
    if not ports:
        return []
    try:
        placement = obj.Placement
    except Exception:
        placement = App.Placement()
    rot = getattr(placement, "Rotation", App.Rotation())
    out = []
    for p in ports:
        if not isinstance(p, dict):
            continue
        name = _safe_text(p.get("name", "")).strip()
        pos = p.get("position", [])
        dvec = p.get("direction", [])
        if not (isinstance(pos, (list, tuple)) and len(pos) >= 3):
            continue
        lp = _vec(pos[0], pos[1], pos[2])
        wp = placement.multVec(lp)
        if isinstance(dvec, (list, tuple)) and len(dvec) >= 3:
            ld = _vec(dvec[0], dvec[1], dvec[2])
            wd = _normalize(rot.multVec(ld))
        else:
            wd = _vec(0.0, 0.0, 0.0)
        out.append({"name": name, "point": wp, "dir": wd})
    if _is_octagon_box(obj):
        return _rename_octagon_ports_world(obj, out)
    return out


def _ordered_cardinal_ports(obj, toward_point):
    base = _anchor_point(obj)
    vt = _normalize(_vec(float(toward_point.x) - float(base.x), float(toward_point.y) - float(base.y), 0.0))
    if _vlen(vt) <= EPS:
        return CARDINAL_PORTS

    if abs(vt.x) >= abs(vt.y):
        primary = "East" if vt.x >= 0.0 else "West"
        secondary = "North" if vt.y >= 0.0 else "South"
    else:
        primary = "North" if vt.y >= 0.0 else "South"
        secondary = "East" if vt.x >= 0.0 else "West"

    opposite = {
        "North": "South",
        "South": "North",
        "East": "West",
        "West": "East",
    }
    ordered = [primary, secondary, opposite.get(primary, ""), opposite.get(secondary, "")]
    out = []
    seen = set()
    for name in ordered + list(CARDINAL_PORTS):
        if name and name not in seen:
            out.append(name)
            seen.add(name)
    return tuple(out)


def _ordered_diagonal_ports(obj, toward_point):
    base = _anchor_point(obj)
    vt = _normalize(_vec(float(toward_point.x) - float(base.x), float(toward_point.y) - float(base.y), 0.0))
    if _vlen(vt) <= EPS:
        return ("NorthEast", "NorthWest", "SouthEast", "SouthWest")

    diag_dirs = {
        "NorthEast": _normalize(_vec(1.0, 1.0, 0.0)),
        "NorthWest": _normalize(_vec(-1.0, 1.0, 0.0)),
        "SouthEast": _normalize(_vec(1.0, -1.0, 0.0)),
        "SouthWest": _normalize(_vec(-1.0, -1.0, 0.0)),
    }
    ranked = sorted(
        list(diag_dirs.items()),
        key=lambda kv: -float(_dot(kv[1], vt)),
    )
    out = []
    seen = set()
    for name, _dir in ranked:
        if name not in seen:
            out.append(name)
            seen.add(name)
    for name in ("NorthEast", "NorthWest", "SouthEast", "SouthWest"):
        if name not in seen:
            out.append(name)
            seen.add(name)
    return tuple(out)


def _is_switch_origin_box(obj):
    if obj is None or (not _is_octagon_box(obj)):
        return False
    txt = (
        f"{_safe_text(getattr(obj, 'CajaOrigenName', ''))} "
        f"{_safe_text(getattr(obj, 'Label', ''))} "
        f"{_safe_text(getattr(obj, 'Name', ''))}"
    ).strip().lower()
    compact = re.sub(r"[\s_\-]+", "", txt)
    if ("3way" in compact) or ("3vias" in compact) or ("tresvias" in compact):
        return True
    return any(tok in txt for tok in ("apagador", "switch", "interruptor", "conmutador", "triway", "threeway"))


def _ordered_all_side_ports(obj, toward_point, include_diagonal=False):
    allowed = set(CARDINAL_PORTS)
    if include_diagonal:
        allowed.update(("NorthEast", "NorthWest", "SouthEast", "SouthWest"))
    ports = [p for p in (_world_ports(obj) or []) if _safe_text(p.get("name", "")).strip() in allowed]
    if not ports:
        if include_diagonal:
            return ("North", "East", "South", "West", "NorthEast", "NorthWest", "SouthEast", "SouthWest")
        return CARDINAL_PORTS

    base = _anchor_point(obj)
    vt = _normalize(
        _vec(
            float(toward_point.x) - float(base.x),
            float(toward_point.y) - float(base.y),
            0.0,
        )
    )
    if _vlen(vt) <= EPS:
        if include_diagonal:
            return ("North", "East", "South", "West", "NorthEast", "NorthWest", "SouthEast", "SouthWest")
        return CARDINAL_PORTS

    ranked = []
    for p in ports:
        name = _safe_text(p.get("name", "")).strip()
        dxy = _normalize(
            _vec(
                float(p["point"].x) - float(base.x),
                float(p["point"].y) - float(base.y),
                0.0,
            )
        )
        if _vlen(dxy) <= EPS:
            dxy = _normalize(_vec(float(p.get("dir", _vec(0.0, 0.0, 0.0)).x), float(p.get("dir", _vec(0.0, 0.0, 0.0)).y), 0.0))
        score = -float(_dot(dxy, vt)) if _vlen(dxy) > EPS else 1e9
        ranked.append((score, name))

    ranked.sort(key=lambda it: (float(it[0]), _safe_text(it[1])))
    out = []
    seen = set()
    for _score, name in ranked:
        if name and name not in seen:
            out.append(name)
            seen.add(name)
    fallback = ("North", "East", "South", "West", "NorthEast", "NorthWest", "SouthEast", "SouthWest") if include_diagonal else CARDINAL_PORTS
    for name in fallback:
        if name not in seen:
            out.append(name)
            seen.add(name)
    return tuple(out)


def _is_luminaria_like(obj):
    if obj is None or _is_group(obj):
        return False
    txt = (
        f"{_safe_text(getattr(obj, 'Tipo', ''))} "
        f"{_safe_text(getattr(obj, 'TipoLogico', ''))} "
        f"{_safe_text(getattr(obj, 'Categoria', ''))} "
        f"{_safe_text(getattr(obj, 'Label', ''))} "
        f"{_safe_text(getattr(obj, 'Name', ''))}"
    ).lower()
    if ("toma" in txt) or ("apagador" in txt) or ("switch" in txt) or ("interruptor" in txt) or ("tablero" in txt):
        return False
    return ("lumin" in txt) or ("lum " in f"{txt} ") or (" lampara" in f" {txt}") or ("luz" in txt)


def _port_point_by_name(obj, port_name):
    want = _safe_text(port_name).strip()
    if not want:
        return None
    for p in (_world_ports(obj) or []):
        if _safe_text(p.get("name", "")).strip() == want:
            return p.get("point")
    return None


def _box_perimeter_join_point(obj, toward_point):
    if obj is None or toward_point is None or not _is_octagon_box(obj):
        return None
    ordered = _ordered_cardinal_ports(obj, toward_point)
    for name in ordered:
        pt = _port_point_by_name(obj, name)
        if pt is not None:
            return pt
    return None


def _is_board_like(obj):
    if obj is None or _is_group(obj):
        return False
    return _fallback_component_type(obj) == "Tablero"


def _anchor_allowed_faces(cfg):
    vals = [_safe_text(x).strip() for x in (cfg.get("anchor_faces", list(BOARD_FACES)) or list(BOARD_FACES)) if _safe_text(x).strip() in BOARD_FACES]
    return vals or list(BOARD_FACES)


def _resolve_anchor_face(obj, toward_point=None, forced_face="Auto", allowed_faces=None):
    allowed = [x for x in (allowed_faces or list(BOARD_FACES)) if _safe_text(x).strip() in BOARD_FACES]
    if not allowed:
        allowed = list(BOARD_FACES)
    face = _safe_text(forced_face).strip()
    if face in BOARD_FACES:
        return face
    base = _anchor_point(obj)
    other = toward_point if toward_point is not None else base
    dx = float(other.x) - float(base.x)
    dy = float(other.y) - float(base.y)
    dz = float(other.z) - float(base.z)
    candidates = [
        ("East", dx if dx > 0.0 else 0.0),
        ("West", -dx if dx < 0.0 else 0.0),
        ("North", dy if dy > 0.0 else 0.0),
        ("South", -dy if dy < 0.0 else 0.0),
        ("Top", dz if dz > 0.0 else 0.0),
        ("Bottom", -dz if dz < 0.0 else 0.0),
    ]
    candidates.sort(key=lambda it: (-float(it[1]), list(BOARD_FACES).index(it[0]) if it[0] in BOARD_FACES else 99))
    for name, score in candidates:
        if score > EPS and name in allowed:
            return name
    return allowed[0]


def _board_tangent_offset(face, lane_scalar):
    val = float(lane_scalar)
    face_txt = _safe_text(face).strip()
    if face_txt in ("West", "East"):
        return -val
    return val


def _board_local_axes(obj):
    x_axis = _vec(1.0, 0.0, 0.0)
    y_axis = _vec(0.0, 1.0, 0.0)
    z_axis = _vec(0.0, 0.0, 1.0)
    try:
        rot = getattr(getattr(obj, "Placement", None), "Rotation", None)
        if rot is not None:
            x_axis = _normalize(rot.multVec(_vec(1.0, 0.0, 0.0)))
            y_axis = _normalize(rot.multVec(_vec(0.0, 1.0, 0.0)))
            z_axis = _normalize(rot.multVec(_vec(0.0, 0.0, 1.0)))
    except Exception:
        pass
    return x_axis, y_axis, z_axis


def _board_local_dimensions(obj, bb):
    width = None
    depth = None
    height = None
    prop_sets = (
        ("Length", "Width", "Height"),
        ("Largo", "Ancho", "Alto"),
        ("XLength", "YLength", "ZLength"),
    )
    for nlen, nwid, nhgt in prop_sets:
        try:
            if all(hasattr(obj, nm) for nm in (nlen, nwid, nhgt)):
                width = _to_float(getattr(obj, nlen), 0.0)
                depth = _to_float(getattr(obj, nwid), 0.0)
                height = _to_float(getattr(obj, nhgt), 0.0)
                if width > EPS and depth > EPS and height > EPS:
                    break
        except Exception:
            pass
    if not (width and width > EPS and depth and depth > EPS and height and height > EPS):
        width = max(EPS, float(getattr(bb, "XMax", 0.0)) - float(getattr(bb, "XMin", 0.0)))
        depth = max(EPS, float(getattr(bb, "YMax", 0.0)) - float(getattr(bb, "YMin", 0.0)))
        height = max(EPS, float(getattr(bb, "ZMax", 0.0)) - float(getattr(bb, "ZMin", 0.0)))
    return float(width), float(depth), float(height)


def _lane_point_in_top_bounds(xmin, xmax, ymin, ymax, lane_index=0, lane_count=1, separation=DEFAULT_CIRCUIT_SEPARATION):
    width = max(EPS, float(xmax) - float(xmin))
    depth = max(EPS, float(ymax) - float(ymin))
    n = max(1, int(lane_count))
    idx = max(0, min(n - 1, int(lane_index)))
    rows = 2 if n > 2 else 1
    if rows == 1:
        row = 0
        col = idx
        row_counts = [n]
    else:
        row0 = int(math.ceil(float(n) / 2.0))
        row1 = max(0, n - row0)
        if idx < row0:
            row = 0
            col = idx
        else:
            row = 1
            col = idx - row0
        row_counts = [row0, max(1, row1)]

    sep = max(0.0, float(separation))
    margin_x = min(max(25.0, sep, 0.12 * width), 0.35 * width)
    margin_y = min(max(20.0, 0.18 * depth), 0.35 * depth)
    x0 = xmin + margin_x
    x1 = xmax - margin_x
    count_row = max(1, int(row_counts[row]))
    if count_row <= 1 or x1 <= x0 + EPS:
        x = 0.5 * (xmin + xmax)
    else:
        x = x0 + (x1 - x0) * (float(col) / float(count_row - 1))
    if rows == 1:
        y = 0.5 * (float(ymin) + float(ymax))
    else:
        y = (float(ymax) - margin_y) if row == 0 else (float(ymin) + margin_y)
    return x, y


def _board_top_lane_point(bb, lane_index=0, lane_count=1, separation=DEFAULT_CIRCUIT_SEPARATION):
    return _lane_point_in_top_bounds(
        float(bb.XMin),
        float(bb.XMax),
        float(bb.YMin),
        float(bb.YMax),
        lane_index=lane_index,
        lane_count=lane_count,
        separation=separation,
    )


def _board_top_section_lane_point(
    bb,
    section_index=0,
    section_count=1,
    lane_index=0,
    lane_count=1,
    separation=DEFAULT_CIRCUIT_SEPARATION,
):
    xmin = float(bb.XMin)
    xmax = float(bb.XMax)
    ymin = float(bb.YMin)
    ymax = float(bb.YMax)
    width = max(EPS, xmax - xmin)
    nsec = max(1, int(section_count))
    sidx = max(0, min(nsec - 1, int(section_index)))
    block_idx = max(0, min(nsec - 1, (nsec - 1) - sidx))
    base_margin = min(max(20.0, 0.08 * width), 0.25 * width)
    span_min = xmin + base_margin
    span_max = xmax - base_margin
    if span_max <= span_min + EPS:
        span_min = xmin
        span_max = xmax
    section_width = max(EPS, (span_max - span_min) / float(nsec))
    sec_xmin = span_min + (section_width * float(block_idx))
    sec_xmax = sec_xmin + section_width
    inner = min(max(12.0, 0.10 * section_width), 0.30 * section_width)
    sec_xmin += inner
    sec_xmax -= inner
    if sec_xmax <= sec_xmin + EPS:
        mid = 0.5 * (sec_xmin + sec_xmax)
        sec_xmin = mid
        sec_xmax = mid
    n = max(1, int(lane_count))
    idx = max(0, min(n - 1, int(lane_index)))
    depth = max(EPS, ymax - ymin)
    sep = max(0.0, float(separation))
    row_pitch = min(max(32.0, min(sep, 40.0)), 0.22 * depth)
    top_margin = min(max(18.0, 0.10 * depth), 0.20 * depth)
    y_top = ymax - top_margin
    y_bottom = max(ymin + top_margin, y_top - row_pitch)
    if n <= 1 or sec_xmax <= sec_xmin + EPS:
        x = 0.5 * (sec_xmin + sec_xmax)
        y = y_top
    else:
        row = int(idx % 2)
        x = sec_xmax - ((sec_xmax - sec_xmin) * (float(idx) / float(n - 1)))
        y = y_top if row == 0 else y_bottom
    return x, y


def _board_face_endpoint(
    obj,
    toward_point=None,
    forced_face="Auto",
    tangent_offset=0.0,
    allowed_faces=None,
    lane_index=0,
    lane_count=1,
    lane_separation=DEFAULT_CIRCUIT_SEPARATION,
    section_index=0,
    section_count=1,
    section_lane_index=0,
    section_lane_count=1,
):
    center = _anchor_point(obj)
    face = _resolve_anchor_face(obj, toward_point=toward_point, forced_face=forced_face, allowed_faces=allowed_faces)
    try:
        bb = getattr(getattr(obj, "Shape", None), "BoundBox", None)
    except Exception:
        bb = None
    if bb is None:
        bb = type("BBox", (), {
            "XMin": float(center.x),
            "XMax": float(center.x),
            "YMin": float(center.y),
            "YMax": float(center.y),
            "ZMin": float(center.z),
            "ZMax": float(center.z),
        })()
    width, depth, height = _board_local_dimensions(obj, bb)
    hx = 0.5 * float(width)
    hy = 0.5 * float(depth)
    hz = 0.5 * float(height)
    x_axis, y_axis, z_axis = _board_local_axes(obj)

    def _point_local(x_local, y_local, z_local):
        return _vec(
            center.x + (x_axis.x * x_local) + (y_axis.x * y_local) + (z_axis.x * z_local),
            center.y + (x_axis.y * x_local) + (y_axis.y * y_local) + (z_axis.y * z_local),
            center.z + (x_axis.z * x_local) + (y_axis.z * y_local) + (z_axis.z * z_local),
        )

    t = float(tangent_offset)
    if face == "North":
        point = _point_local(t, hy, 0.0)
        direction = y_axis
    elif face == "South":
        point = _point_local(t, -hy, 0.0)
        direction = _vec(-y_axis.x, -y_axis.y, -y_axis.z)
    elif face == "West":
        point = _point_local(-hx, t, 0.0)
        direction = _vec(-x_axis.x, -x_axis.y, -x_axis.z)
    elif face == "Top":
        top_x, top_y = _board_top_section_lane_point(
            type("LocalBBox", (), {"XMin": -hx, "XMax": hx, "YMin": -hy, "YMax": hy})(),
            section_index=section_index,
            section_count=section_count,
            lane_index=section_lane_index,
            lane_count=section_lane_count,
            separation=lane_separation,
        )
        point = _point_local(top_x, top_y, hz)
        direction = z_axis
    elif face == "Bottom":
        bot_x, bot_y = _board_top_section_lane_point(
            type("LocalBBox", (), {"XMin": -hx, "XMax": hx, "YMin": -hy, "YMax": hy})(),
            section_index=section_index,
            section_count=section_count,
            lane_index=section_lane_index,
            lane_count=section_lane_count,
            separation=lane_separation,
        )
        point = _point_local(bot_x, bot_y, -hz)
        direction = _vec(-z_axis.x, -z_axis.y, -z_axis.z)
    else:
        point = _point_local(hx, t, 0.0)
        direction = x_axis
    return {"point": point, "port": face, "dir": direction}


def _reserve_perimeter_box_endpoint(obj, toward_point, used_ports, reserve_ports=True):
    if not _is_octagon_box(obj):
        pt = _box_perimeter_join_point(obj, toward_point)
        if pt is None:
            pt = _anchor_point(obj)
        return {"point": pt, "port": "", "dir": _vec(0.0, 0.0, 0.0)}
    ordered = _ordered_cardinal_ports(obj, toward_point)
    return _select_endpoint(
        obj,
        toward_point,
        used_ports,
        reserve_ports=reserve_ports,
        prefer_port_names=ordered,
        strict_preferred=True,
        candidate_port_names=OCTAGON_SIDE_PORTS,
        avoid_reuse=True,
    )


def _ordered_outward_cardinal_ports(obj, rect):
    if obj is None or rect is None:
        return CARDINAL_PORTS
    xmin, xmax, ymin, ymax = rect
    center = _vec(0.5 * (xmin + xmax), 0.5 * (ymin + ymax), 0.0)
    base = _anchor_point(obj)
    vt = _normalize(_vec(float(base.x) - float(center.x), float(base.y) - float(center.y), 0.0))
    if _vlen(vt) <= EPS:
        return CARDINAL_PORTS

    if abs(vt.x) >= abs(vt.y):
        primary = "East" if vt.x >= 0.0 else "West"
        secondary = "North" if vt.y >= 0.0 else "South"
    else:
        primary = "North" if vt.y >= 0.0 else "South"
        secondary = "East" if vt.x >= 0.0 else "West"

    opposite = {
        "North": "South",
        "South": "North",
        "East": "West",
        "West": "East",
    }
    ordered = [primary, secondary, opposite.get(secondary, ""), opposite.get(primary, "")]
    out = []
    seen = set()
    for name in ordered + list(CARDINAL_PORTS):
        if name and name not in seen:
            out.append(name)
            seen.add(name)
    return tuple(out)


def _select_endpoint(
    obj,
    toward_point,
    used_ports,
    reserve_ports=True,
    prefer_port_names=None,
    strict_preferred=False,
    candidate_port_names=None,
    avoid_reuse=False,
):
    ports = _world_ports(obj)
    allowed = {_safe_text(x).strip() for x in (candidate_port_names or []) if _safe_text(x).strip()}
    if allowed:
        ports = [p for p in ports if _safe_text(p.get("name", "")).strip() in allowed]
    if not ports:
        return {"point": _anchor_point(obj), "port": "", "dir": _vec(0.0, 0.0, 0.0)}

    used = used_ports.get(_safe_text(getattr(obj, "Name", "")), set())
    free_ports = [p for p in ports if p.get("name", "") not in used] if reserve_ports else list(ports)
    cands = list(free_ports)
    if not cands:
        cands = list(ports)

    pref_order = [_safe_text(x).strip() for x in (prefer_port_names or []) if _safe_text(x).strip()]
    pref_rank = {name: idx for idx, name in enumerate(pref_order)}
    pref = set(pref_order)
    if pref_order:
        preferred_all = [p for p in ports if _safe_text(p.get("name", "")).strip() in pref]
        preferred_free = [p for p in free_ports if _safe_text(p.get("name", "")).strip() in pref]
        if strict_preferred:
            # Estricto: solo cardinales preferidos. Si ya se usaron, se permite reusar cardinal
            # antes de caer a diagonales.
            eval_cands = preferred_free if preferred_free else preferred_all
            if avoid_reuse and (not preferred_free) and free_ports:
                eval_cands = list(free_ports)
            if not eval_cands:
                return {"point": _anchor_point(obj), "port": "", "dir": _vec(0.0, 0.0, 0.0)}
        else:
            eval_cands = preferred_free if preferred_free else cands
            if avoid_reuse and (not preferred_free) and free_ports:
                eval_cands = list(free_ports)
    else:
        eval_cands = cands

    best = None
    best_score = None
    for p in eval_cands:
        pp = p["point"]
        d = pp.distanceToPoint(toward_point)
        v = _normalize(toward_point - pp)
        align = _dot(p["dir"], v) if _vlen(p["dir"]) > EPS and _vlen(v) > EPS else 0.0
        score = float(d) + float((1.0 - align) * 250.0)
        if pref_rank:
            pname = _safe_text(p.get("name", "")).strip()
            rank = pref_rank.get(pname, len(pref_rank))
            score += float(rank) * 1e5
        if best is None or score < best_score:
            best = p
            best_score = score

    if best is None:
        return {"point": _anchor_point(obj), "port": "", "dir": _vec(0.0, 0.0, 0.0)}

    pname = _safe_text(best.get("name", ""))
    if reserve_ports and pname:
        obj_name = _safe_text(getattr(obj, "Name", ""))
        used_ports.setdefault(obj_name, set()).add(pname)
    return {"point": best["point"], "port": pname, "dir": best.get("dir", _vec(0.0, 0.0, 0.0))}


def _dedup_points(points):
    out = []
    for p in (points or []):
        if not out:
            out.append(p)
            continue
        if out[-1].distanceToPoint(p) > 0.1:
            out.append(p)
    return out


def _route_crosses_box_interior_xy(obj, points, margin=2.0):
    pts = list(points or [])
    if obj is None or len(pts) < 3:
        return False
    try:
        shape = getattr(obj, "Shape", None)
        if shape is None or shape.isNull():
            return False
        bb = shape.BoundBox
    except Exception:
        return False
    xmin = float(bb.XMin) + float(margin)
    xmax = float(bb.XMax) - float(margin)
    ymin = float(bb.YMin) + float(margin)
    ymax = float(bb.YMax) - float(margin)
    if xmin >= xmax or ymin >= ymax:
        return False
    for p in pts[1:-1]:
        x = float(p.x)
        y = float(p.y)
        if (xmin < x < xmax) and (ymin < y < ymax):
            return True
    return False


def _simplify_orthogonal_points(points):
    pts = _dedup_points(points)
    if len(pts) < 3:
        return pts

    def _segment_axis(a, b):
        dx = abs(float(b.x) - float(a.x))
        dy = abs(float(b.y) - float(a.y))
        dz = abs(float(b.z) - float(a.z))
        axes = []
        if dx > 0.1:
            axes.append("x")
        if dy > 0.1:
            axes.append("y")
        if dz > 0.1:
            axes.append("z")
        if len(axes) == 1:
            return axes[0]
        if not axes:
            return ""
        return "".join(axes)

    def _axis_delta(a, b, axis):
        if axis == "x":
            return float(b.x) - float(a.x)
        if axis == "y":
            return float(b.y) - float(a.y)
        if axis == "z":
            return float(b.z) - float(a.z)
        return 0.0

    changed = True
    while changed and len(pts) >= 3:
        changed = False
        out = [pts[0]]
        for i in range(1, len(pts) - 1):
            a = out[-1]
            b = pts[i]
            c = pts[i + 1]
            axis_ab = _segment_axis(a, b)
            axis_bc = _segment_axis(b, c)

            # Solo simplificar segmentos rectos sobre el mismo eje.
            # Si cambia de Y a Z, por ejemplo, es un codo valido y no debe borrarse.
            if axis_ab and axis_ab == axis_bc and axis_ab in ("x", "y", "z"):
                dab = _axis_delta(a, b, axis_ab)
                dbc = _axis_delta(b, c, axis_ab)
                # Colineal con misma direccion: remover punto intermedio.
                if (dab * dbc) >= 0.0:
                    changed = True
                    continue
                # Reversion inmediata sobre el mismo eje: conservar extremo mas alejado.
                if abs(_axis_delta(a, c, axis_ab)) >= abs(dab):
                    changed = True
                    continue

            out.append(b)
        out.append(pts[-1])
        pts = _dedup_points(out)
    return pts


def _trim_endpoint_backtrack(points):
    pts = _dedup_points(points)
    if len(pts) < 3:
        return pts

    def _axis_and_delta(a, b):
        dx = float(b.x) - float(a.x)
        dy = float(b.y) - float(a.y)
        dz = float(b.z) - float(a.z)
        axes = []
        if abs(dx) > 0.1:
            axes.append(("x", dx))
        if abs(dy) > 0.1:
            axes.append(("y", dy))
        if abs(dz) > 0.1:
            axes.append(("z", dz))
        if len(axes) != 1:
            return "", 0.0
        return axes[0][0], float(axes[0][1])

    changed = True
    while changed and len(pts) >= 3:
        changed = False
        # Inicio: A->B->C sobre mismo eje y en sentido opuesto.
        ax1, d1 = _axis_and_delta(pts[0], pts[1])
        ax2, d2 = _axis_and_delta(pts[1], pts[2])
        if ax1 and ax1 == ax2 and (d1 * d2) < 0.0:
            del pts[1]
            pts = _dedup_points(pts)
            changed = True
            continue
        # Final: ...A->B->C sobre mismo eje y en sentido opuesto.
        ax1, d1 = _axis_and_delta(pts[-3], pts[-2])
        ax2, d2 = _axis_and_delta(pts[-2], pts[-1])
        if ax1 and ax1 == ax2 and (d1 * d2) < 0.0:
            del pts[-2]
            pts = _dedup_points(pts)
            changed = True
    return pts


def _bbox_xy(points):
    pts = [p for p in (points or []) if p is not None]
    if not pts:
        return None
    xs = [float(p.x) for p in pts]
    ys = [float(p.y) for p in pts]
    return (min(xs), max(xs), min(ys), max(ys))


def _expand_rect(rect, margin):
    if rect is None:
        return None
    xmin, xmax, ymin, ymax = rect
    m = max(0.0, float(margin))
    xmin -= m
    xmax += m
    ymin -= m
    ymax += m
    if (xmax - xmin) < 200.0:
        c = 0.5 * (xmin + xmax)
        xmin, xmax = c - 100.0, c + 100.0
    if (ymax - ymin) < 200.0:
        c = 0.5 * (ymin + ymax)
        ymin, ymax = c - 100.0, c + 100.0
    return (xmin, xmax, ymin, ymax)


def _offset_rect(rect, vec):
    if rect is None:
        return None
    xmin, xmax, ymin, ymax = rect
    dx = float(getattr(vec, "x", 0.0) or 0.0)
    dy = float(getattr(vec, "y", 0.0) or 0.0)
    return (xmin + dx, xmax + dx, ymin + dy, ymax + dy)


def _clamp(v, lo, hi):
    return max(float(lo), min(float(hi), float(v)))


def _nearest_rect_edge_point(p, rect, z):
    xmin, xmax, ymin, ymax = rect
    cands = [
        (_vec(_clamp(p.x, xmin, xmax), ymin, z), 0),  # bottom
        (_vec(xmax, _clamp(p.y, ymin, ymax), z), 1),  # right
        (_vec(_clamp(p.x, xmin, xmax), ymax, z), 2),  # top
        (_vec(xmin, _clamp(p.y, ymin, ymax), z), 3),  # left
    ]
    best = None
    best_d = None
    for pt, edge in cands:
        d = pt.distanceToPoint(_vec(p.x, p.y, z))
        if best is None or d < best_d:
            best = (pt, edge)
            best_d = d
    return best


def _rect_edge_point(p, rect, z, edge):
    if rect is None:
        return None
    xmin, xmax, ymin, ymax = rect
    e = int(edge)
    if e == 0:
        return _vec(_clamp(p.x, xmin, xmax), ymin, z), 0
    if e == 1:
        return _vec(xmax, _clamp(p.y, ymin, ymax), z), 1
    if e == 2:
        return _vec(_clamp(p.x, xmin, xmax), ymax, z), 2
    if e == 3:
        return _vec(xmin, _clamp(p.y, ymin, ymax), z), 3
    return _nearest_rect_edge_point(p, rect, z)


def _preferred_rect_edge_for_port(port_name):
    name = _safe_text(port_name).strip()
    mapping = {
        "South": 0,
        "East": 1,
        "North": 2,
        "West": 3,
    }
    return mapping.get(name)


def _rect_params(rect):
    xmin, xmax, ymin, ymax = rect
    w = max(float(xmax - xmin), 1e-3)
    h = max(float(ymax - ymin), 1e-3)
    L = 2.0 * (w + h)
    return xmin, xmax, ymin, ymax, w, h, L


def _rect_point_to_s(p, edge, rect):
    xmin, xmax, ymin, ymax, w, h, _L = _rect_params(rect)
    if edge == 0:
        return _clamp(p.x, xmin, xmax) - xmin
    if edge == 1:
        return w + (_clamp(p.y, ymin, ymax) - ymin)
    if edge == 2:
        return w + h + (xmax - _clamp(p.x, xmin, xmax))
    return 2.0 * w + h + (ymax - _clamp(p.y, ymin, ymax))


def _rect_s_to_point(s, rect, z):
    xmin, xmax, ymin, ymax, w, h, L = _rect_params(rect)
    t = float(s) % L
    if t <= w:
        return _vec(xmin + t, ymin, z)
    t -= w
    if t <= h:
        return _vec(xmax, ymin + t, z)
    t -= h
    if t <= w:
        return _vec(xmax - t, ymax, z)
    t -= w
    return _vec(xmin, ymax - t, z)


def _perimeter_polyline_cw(rect, s_from, s_to, z):
    xmin, xmax, ymin, ymax, w, h, L = _rect_params(rect)
    _ = (xmin, xmax, ymin, ymax)  # silence linters
    a = float(s_from)
    b = float(s_to)
    if b < a:
        b += L
    corner_base = [0.0, w, w + h, 2.0 * w + h, L]
    mids = []
    for m in (0.0, L):
        for c in corner_base:
            v = c + m
            if a < v < b:
                mids.append(v)
    mids = sorted(set(mids))

    pts = [_rect_s_to_point(a, rect, z)]
    for v in mids:
        pts.append(_rect_s_to_point(v, rect, z))
    pts.append(_rect_s_to_point(b, rect, z))
    return _dedup_points(pts)


def _polyline_len(pts):
    total = 0.0
    for a, b in zip(pts[:-1], pts[1:]):
        total += float(a.distanceToPoint(b))
    return total


def _distance_xy(a, b):
    dx = float(a.x) - float(b.x)
    dy = float(a.y) - float(b.y)
    return (dx * dx + dy * dy) ** 0.5


def _project_point_to_segment_xy(p, a, b):
    abx = float(b.x) - float(a.x)
    aby = float(b.y) - float(a.y)
    den = (abx * abx) + (aby * aby)
    if den <= EPS:
        proj = _vec(a.x, a.y, 0.0)
        return proj, 0.0, _distance_xy(p, proj)
    apx = float(p.x) - float(a.x)
    apy = float(p.y) - float(a.y)
    t = ((apx * abx) + (apy * aby)) / den
    t = _clamp(t, 0.0, 1.0)
    proj = _vec(float(a.x) + (abx * t), float(a.y) + (aby * t), 0.0)
    return proj, t, _distance_xy(p, proj)


def _line_intersection_xy(p1, d1, p2, d2):
    a = float(d1.x)
    b = -float(d2.x)
    c = float(d1.y)
    d = -float(d2.y)
    det = (a * d) - (b * c)
    if abs(det) <= EPS:
        return None
    dx = float(p2.x) - float(p1.x)
    dy = float(p2.y) - float(p1.y)
    t = ((dx * d) - (b * dy)) / det
    return _vec(float(p1.x) + (t * float(d1.x)), float(p1.y) + (t * float(d1.y)), float(p1.z))


def _offset_polyline_xy_manual(pts, offset_dist):
    pts0 = _dedup_points(pts)
    d = float(offset_dist)
    if len(pts0) < 2 or abs(d) <= EPS:
        return pts0

    segs = []
    for a, b in zip(pts0[:-1], pts0[1:]):
        dx = float(b.x) - float(a.x)
        dy = float(b.y) - float(a.y)
        seg_len = (dx * dx + dy * dy) ** 0.5
        if seg_len <= EPS:
            continue
        nx = -dy / seg_len
        ny = dx / seg_len
        off = _vec(nx * d, ny * d, 0.0)
        segs.append({
            "a": _vec(float(a.x) + off.x, float(a.y) + off.y, float(a.z)),
            "b": _vec(float(b.x) + off.x, float(b.y) + off.y, float(b.z)),
            "dir": _vec(dx / seg_len, dy / seg_len, 0.0),
        })
    if len(segs) < 1:
        return pts0

    out = [segs[0]["a"]]
    for prev, cur in zip(segs[:-1], segs[1:]):
        inter = _line_intersection_xy(prev["a"], prev["dir"], cur["a"], cur["dir"])
        if inter is None:
            out.append(prev["b"])
        else:
            out.append(inter)
    out.append(segs[-1]["b"])
    return _dedup_points(out)


def _polyline_offset_vector_xy(pts, offset_dist):
    pts0 = _dedup_points(pts)
    d = float(offset_dist)
    if len(pts0) < 2 or abs(d) <= EPS:
        return _vec(0.0, 0.0, 0.0)
    for a, b in zip(pts0[:-1], pts0[1:]):
        dx = float(b.x) - float(a.x)
        dy = float(b.y) - float(a.y)
        seg_len = (dx * dx + dy * dy) ** 0.5
        if seg_len > EPS:
            return _vec((-dy / seg_len) * d, (dx / seg_len) * d, 0.0)
    return _vec(0.0, 0.0, 0.0)


def _part_wire_from_polyline_xy(pts):
    if Part is None:
        return None
    pts0 = _dedup_points(pts)
    if len(pts0) < 2:
        return None
    edges = []
    z = float(pts0[0].z)
    for a, b in zip(pts0[:-1], pts0[1:]):
        if _distance_xy(a, b) <= EPS:
            continue
        try:
            edges.append(Part.LineSegment(_vec(a.x, a.y, z), _vec(b.x, b.y, z)).toShape())
        except Exception:
            continue
    if not edges:
        return None
    try:
        return Part.Wire(edges)
    except Exception:
        try:
            return Part.Wire(Part.__sortEdges__(edges))
        except Exception:
            return None


def _polyline_points_from_wire_xy(wire, z_level):
    if wire is None or Part is None:
        return []
    cur = wire
    try:
        wires = list(getattr(cur, "Wires", []) or [])
        if wires:
            cur = wires[0]
    except Exception:
        pass
    edges = list(getattr(cur, "Edges", []) or [])
    if not edges:
        return []
    try:
        edges = Part.__sortEdges__(edges)
    except Exception:
        pass
    pts = []
    for edge in edges:
        verts = list(getattr(edge, "Vertexes", []) or [])
        if len(verts) >= 1:
            p0 = verts[0].Point
            pts.append(_vec(p0.x, p0.y, z_level))
        if len(verts) >= 2:
            p1 = verts[-1].Point
            pts.append(_vec(p1.x, p1.y, z_level))
    return _dedup_points(pts)


def _offset_polyline_xy(pts, offset_dist):
    pts0 = _dedup_points(pts)
    d = float(offset_dist)
    if len(pts0) < 2 or abs(d) <= EPS:
        return pts0

    dvec = _polyline_offset_vector_xy(pts0, d)
    if _vlen(dvec) <= EPS:
        return pts0

    wire = _part_wire_from_polyline_xy(pts0)
    if wire is None:
        App.Console.PrintMessage(f"{TAG}[DEBUG] Offset aplicado | distancia={d:.1f} mm | metodo=fallback-manual\n")
        _debug(f"Offset polilinea fallback manual | distancia={d:.1f} | razon=sin_wire")
        return _offset_polyline_xy_manual(pts0, d)

    App.Console.PrintMessage(
        f"{TAG}[DEBUG] Offset aplicado | distancia={d:.1f} mm | dvec={_fmt_vec(dvec)} | metodo=offsetWire\n"
    )
    _debug(f"Offset polilinea | distancia={d:.1f} | dvec={_fmt_vec(dvec)} | puntos_base={_fmt_points(pts0)}")

    offset_wire = None
    errors = []
    if DraftOffsets is not None and hasattr(DraftOffsets, "offsetWire"):
        try:
            offset_wire = DraftOffsets.offsetWire(wire, dvec)
        except Exception as ex:
            errors.append(f"draftgeoutils.offsets.offsetWire: {ex}")
    if offset_wire is None and DraftGeomUtils is not None and hasattr(DraftGeomUtils, "offsetWire"):
        try:
            offset_wire = DraftGeomUtils.offsetWire(wire, dvec)
        except Exception as ex:
            errors.append(f"DraftGeomUtils.offsetWire: {ex}")

    pts_off = _polyline_points_from_wire_xy(offset_wire, float(pts0[0].z))
    if len(pts_off) >= 2:
        _debug(f"Offset polilinea OK | distancia={d:.1f} | puntos_offset={_fmt_points(pts_off)}")
        return pts_off

    if errors:
        _debug("Offset polilinea fallback manual | " + " | ".join(errors))
    App.Console.PrintMessage(f"{TAG}[DEBUG] Offset aplicado | distancia={d:.1f} mm | metodo=fallback-manual\n")
    return _offset_polyline_xy_manual(pts0, d)


def _offset_route_planar_segment(points, z_level, offset_dist, context_tag=""):
    pts0 = _dedup_points(points)
    d = float(offset_dist)
    if len(pts0) < 3 or abs(d) <= EPS:
        return pts0

    z_ref = float(z_level)
    planar_ids = [idx for idx, pt in enumerate(pts0) if abs(float(pt.z) - z_ref) <= 0.1]
    if len(planar_ids) < 2:
        return pts0

    i0 = int(planar_ids[0])
    i1 = int(planar_ids[-1])
    if i1 <= i0:
        return pts0

    base_planar = [_vec(pt.x, pt.y, z_ref) for pt in pts0[i0:i1 + 1]]
    if len(base_planar) < 2:
        return pts0

    offset_planar = _offset_polyline_xy(base_planar, d)
    if len(offset_planar) < 2:
        return pts0

    out = list(pts0[:i0 + 1])
    if out[-1].distanceToPoint(offset_planar[0]) > 0.1:
        out.append(offset_planar[0])
    for pt in offset_planar[1:-1]:
        out.append(pt)
    if offset_planar[-1].distanceToPoint(pts0[i1]) > 0.1:
        out.append(offset_planar[-1])
    out.extend(list(pts0[i1:]))
    out = _dedup_points(out)

    tag = _safe_text(context_tag).strip() or "-"
    App.Console.PrintMessage(
        f"{TAG}[DEBUG] Offset de ruta plana aplicado | distancia={d:.1f} mm | contexto={tag}\n"
    )
    _debug(
        f"Offset ruta plana | contexto={tag} | distancia={d:.1f} | "
        f"segmento_z={z_ref:.1f} | base={_fmt_points(base_planar)} | offset={_fmt_points(offset_planar)}"
    )
    return out


def _project_point_to_polyline_xy(p, pts):
    if len(pts or []) < 2:
        return None
    best = None
    acc = 0.0
    for idx, (a, b) in enumerate(zip(pts[:-1], pts[1:])):
        seg_len = _distance_xy(a, b)
        proj, t, dist = _project_point_to_segment_xy(p, a, b)
        s = acc + (seg_len * float(t))
        item = {
            "index": idx,
            "point": proj,
            "distance": float(dist),
            "s": float(s),
        }
        if best is None or float(item["distance"]) < float(best["distance"]):
            best = item
        acc += seg_len
    return best


def _guide_path_between(pts, proj_a, proj_b, z):
    if proj_a is None or proj_b is None:
        return []
    pa = _vec(proj_a["point"].x, proj_a["point"].y, z)
    pb = _vec(proj_b["point"].x, proj_b["point"].y, z)
    if int(proj_a["index"]) == int(proj_b["index"]):
        return _dedup_points([pa, pb])

    out = [pa]
    if float(proj_a["s"]) <= float(proj_b["s"]):
        for idx in range(int(proj_a["index"]) + 1, int(proj_b["index"]) + 1):
            v = pts[idx]
            out.append(_vec(v.x, v.y, z))
    else:
        for idx in range(int(proj_a["index"]), int(proj_b["index"]), -1):
            v = pts[idx]
            out.append(_vec(v.x, v.y, z))
    out.append(pb)
    return _dedup_points(out)


def _guide_hint_point_for_endpoint(guide_info, end, z_level):
    if not guide_info:
        return None
    proj_a = guide_info.get("src_proj")
    proj_b = guide_info.get("dst_proj")
    pts = guide_info.get("points", [])
    path = _guide_path_between(pts, proj_a, proj_b, z_level)
    if end == "src":
        if len(path) >= 2:
            p = path[1]
            return _vec(p.x, p.y, z_level)
        gp = (proj_a or {}).get("point")
    else:
        if len(path) >= 2:
            p = path[-2]
            return _vec(p.x, p.y, z_level)
        gp = (proj_b or {}).get("point")
    if gp is None:
        return None
    return _vec(gp.x, gp.y, z_level)


def _best_guide_for_pair(p1, p2, guide_objs, offset_vec=None, offset_scalar=0.0, prefer_start=False):
    best = None
    off = offset_vec if offset_vec is not None else _vec(0.0, 0.0, 0.0)
    for obj in (guide_objs or []):
        pts0 = _polyline_points_from_object(obj)
        pts = [_vec(pt.x + off.x, pt.y + off.y, pt.z) for pt in pts0]
        if abs(float(offset_scalar)) > EPS:
            pts = _offset_polyline_xy(pts, float(offset_scalar))
        if len(pts) < 2:
            continue
        pr1 = _project_point_to_polyline_xy(p1, pts)
        pr2 = _project_point_to_polyline_xy(p2, pts)
        if pr1 is None or pr2 is None:
            continue
        cost = float(pr1["distance"]) + float(pr2["distance"]) + abs(float(pr2["s"]) - float(pr1["s"]))
        item = {
            "obj": obj,
            "points": pts,
            "src_proj": pr1,
            "dst_proj": pr2,
            "cost": cost,
        }
        if prefer_start:
            key = (float(pr1["distance"]), float(item["cost"]))
            best_key = None if best is None else (float(best["src_proj"]["distance"]), float(best["cost"]))
            if best is None or key < best_key:
                best = item
        elif best is None or float(item["cost"]) < float(best["cost"]):
                best = item
    return best


def _guide_candidates_for_section(guide_objs, section_key):
    key = _safe_text(section_key).strip()
    if not key:
        return list(guide_objs or [])
    if key == "AUTO":
        return []
    return [
        obj
        for obj in (guide_objs or [])
        if _safe_text(getattr(obj, "Name", "")).strip() == key
    ]


def _perimeter_shortest_path(rect, s1, s2, z):
    cw = _perimeter_polyline_cw(rect, s1, s2, z)
    ccw = list(reversed(_perimeter_polyline_cw(rect, s2, s1, z)))
    if _polyline_len(cw) <= _polyline_len(ccw):
        return cw
    return ccw


def _orth2d(a, b, z, final_axis=None):
    p1 = _vec(a.x, a.y, z)
    p2 = _vec(b.x, b.y, z)
    axis = _safe_text(final_axis).strip().lower()
    if axis == "x":
        return _dedup_points([p1, _vec(p1.x, p2.y, z), p2])
    return _dedup_points([p1, _vec(p2.x, p1.y, z), p2])


def _route_points_perimeter(p1, p2, z_level, rect, final_axis=None, src_port=None, dst_port=None):
    z = max(float(z_level), float(p1.z), float(p2.z))
    edge1 = _preferred_rect_edge_for_port(src_port)
    edge2 = _preferred_rect_edge_for_port(dst_port)
    near1 = _rect_edge_point(p1, rect, z, edge1) if edge1 is not None else _nearest_rect_edge_point(p1, rect, z)
    near2 = _rect_edge_point(p2, rect, z, edge2) if edge2 is not None else _nearest_rect_edge_point(p2, rect, z)
    if near1 is None or near2 is None:
        return _dedup_points([p1, _vec(p1.x, p1.y, z), _vec(p2.x, p1.y, z), _vec(p2.x, p2.y, z), p2])

    q1, e1 = near1
    q2, e2 = near2
    s1 = _rect_point_to_s(q1, e1, rect)
    s2 = _rect_point_to_s(q2, e2, rect)
    rim = _perimeter_shortest_path(rect, s1, s2, z)

    pts = [p1, _vec(p1.x, p1.y, z)]
    pts.extend(_orth2d(pts[-1], q1, z)[1:])
    if rim:
        pts.extend(rim[1:])
    pts.extend(_orth2d(pts[-1], q2, z)[1:])
    pts.extend(_orth2d(pts[-1], _vec(p2.x, p2.y, z), z, final_axis=final_axis)[1:])
    pts.append(p2)
    return _dedup_points(pts)


def _route_points_via_guide(p1, p2, z_level, guide_info, final_axis=None, entry_axis=None):
    if not guide_info:
        return _dedup_points([p1, p2])
    z = max(float(z_level), float(p1.z), float(p2.z))
    gp1 = guide_info.get("src_proj")
    gp2 = guide_info.get("dst_proj")
    guide_pts = _guide_path_between(guide_info.get("points", []), gp1, gp2, z)
    if not guide_pts:
        return _dedup_points([p1, _vec(p1.x, p1.y, z), _vec(p2.x, p2.y, z), p2])
    pts = [p1, _vec(p1.x, p1.y, z)]
    pts.extend(_orth2d(pts[-1], guide_pts[0], z, final_axis=entry_axis)[1:])
    pts.extend(guide_pts[1:])
    pts.extend(_orth2d(pts[-1], _vec(p2.x, p2.y, z), z, final_axis=final_axis)[1:])
    pts.append(p2)
    return _dedup_points(pts)


def _route_points(p1, p2, z_level, orthogonal=True, route_by_perimeter=False, rect=None, guide_info=None, final_axis=None, src_port=None, dst_port=None, entry_axis=None):
    if guide_info is not None:
        return _route_points_via_guide(
            p1,
            p2,
            z_level=z_level,
            guide_info=guide_info,
            final_axis=final_axis,
            entry_axis=entry_axis,
        )
    if route_by_perimeter and rect is not None:
        return _route_points_perimeter(
            p1,
            p2,
            z_level=z_level,
            rect=rect,
            final_axis=final_axis,
            src_port=src_port,
            dst_port=dst_port,
        )
    if not orthogonal:
        return _dedup_points([p1, p2])
    z = max(float(z_level), float(p1.z), float(p2.z))
    pts = [p1]
    pts.append(_vec(p1.x, p1.y, z))
    if _safe_text(final_axis).strip().lower() == "x":
        pts.append(_vec(p1.x, p2.y, z))
    else:
        pts.append(_vec(p2.x, p1.y, z))
    pts.append(_vec(p2.x, p2.y, z))
    pts.append(_vec(p2.x, p2.y, p2.z))
    return _dedup_points(pts)


def _make_wire(points):
    maker = getattr(Draft, "make_wire", None)
    if maker is None:
        maker = getattr(Draft, "makeWire", None)
    if maker is None:
        maker = None

    attempts = []
    if maker is not None:
        attempts = [
            lambda: maker(points, False, False, None),
            lambda: maker(points, False, False),
            lambda: maker(points, False),
            lambda: maker(points),
        ]
    last_err = None
    for fn in attempts:
        try:
            return fn()
        except Exception as ex:
            last_err = ex
    doc = App.ActiveDocument
    if Part is not None and doc is not None:
        try:
            shape = Part.makePolygon(points)
            wire = doc.addObject("Part::Feature", "Wire")
            wire.Shape = shape
            return wire
        except Exception as ex:
            last_err = ex
    if maker is None:
        raise RuntimeError("No se encontro Draft.make_wire ni Draft.makeWire")
    raise RuntimeError(f"No se pudo crear Wire: {last_err}")


def _ensure_property(obj, ptype, pname, pgroup, pdesc):
    try:
        if pname not in obj.PropertiesList:
            obj.addProperty(ptype, pname, pgroup, pdesc)
    except Exception:
        pass


def _set_wire_metadata(
    wire,
    conduit_type,
    diameter,
    bend_radius,
    circuit_id,
    src_obj,
    dst_obj,
    src_port,
    dst_port,
    link_kind,
    route_key,
):
    defs = [
        ("App::PropertyString", "Tipo", "ElectricCR", "Tipo logico de objeto"),
        ("App::PropertyString", "ConduitType", "ElectricCR", "Tipo de canalizacion"),
        ("App::PropertyFloat", "DiametroConduit", "ElectricCR", "Diametro de canalizacion (mm)"),
        ("App::PropertyFloat", "RadioCurvatura", "ElectricCR", "Radio de curvatura (mm)"),
        ("App::PropertyString", "CircuitoID", "Circuito", "Identificador de circuito"),
        ("App::PropertyString", "OrigenName", "Vinculo", "Objeto origen"),
        ("App::PropertyString", "DestinoName", "Vinculo", "Objeto destino"),
        ("App::PropertyString", "PuertoOrigen", "Vinculo", "Puerto origen"),
        ("App::PropertyString", "PuertoDestino", "Vinculo", "Puerto destino"),
        ("App::PropertyString", "LinkKind", "Vinculo", "Tipo de enlace generado"),
        ("App::PropertyString", "AutoRouteKey", "Vinculo", "Llave unica para evitar duplicados"),
        ("App::PropertyString", "GeneradoPor", "Vinculo", "Macro generadora"),
    ]
    for ptype, pname, pgroup, pdesc in defs:
        _ensure_property(wire, ptype, pname, pgroup, pdesc)

    try:
        wire.Tipo = "ConduitPath"
    except Exception:
        pass
    try:
        wire.ConduitType = _safe_text(conduit_type)
    except Exception:
        pass
    try:
        wire.DiametroConduit = float(diameter)
    except Exception:
        pass
    try:
        wire.RadioCurvatura = float(bend_radius)
    except Exception:
        pass
    try:
        wire.CircuitoID = _safe_text(circuit_id)
    except Exception:
        pass
    try:
        wire.OrigenName = _safe_text(getattr(src_obj, "Name", ""))
    except Exception:
        pass
    try:
        wire.DestinoName = _safe_text(getattr(dst_obj, "Name", ""))
    except Exception:
        pass
    try:
        wire.PuertoOrigen = _safe_text(src_port)
    except Exception:
        pass
    try:
        wire.PuertoDestino = _safe_text(dst_port)
    except Exception:
        pass
    try:
        wire.LinkKind = _safe_text(link_kind)
    except Exception:
        pass
    try:
        wire.AutoRouteKey = _safe_text(route_key)
    except Exception:
        pass
    try:
        wire.GeneradoPor = "Conectar_Cajas_a_Tablero_Auto"
    except Exception:
        pass


def _style_wire(wire, conduit_type, bend_radius):
    if wire is None or not GUI_UP or not hasattr(wire, "ViewObject"):
        vo = getattr(wire, "ViewObject", None)
    else:
        vo = wire.ViewObject
    # Si Draft Wire soporta FilletRadius, aplicar radio real de codo.
    try:
        if hasattr(wire, "FilletRadius"):
            wire.FilletRadius = max(0.0, float(bend_radius))
    except Exception:
        pass
    if vo is None:
        return
    ctype = _safe_text(conduit_type).upper()
    color = (0.07, 0.31, 0.58) if ctype == "EMT" else (0.72, 0.34, 0.08)
    try:
        vo.LineColor = color
    except Exception:
        pass
    try:
        vo.LineWidth = 2.0
    except Exception:
        pass


def _connection_key(circuit_id, a_obj, b_obj, a_port, b_port):
    a_name = _safe_text(getattr(a_obj, "Name", ""))
    b_name = _safe_text(getattr(b_obj, "Name", ""))
    a_end = f"{a_name}:{_safe_text(a_port)}"
    b_end = f"{b_name}:{_safe_text(b_port)}"
    e1, e2 = sorted([a_end, b_end])
    return f"{_safe_text(circuit_id)}|{e1}|{e2}"


def _collect_existing_route_keys(group_obj):
    keys = set()
    if group_obj is None:
        return keys
    seen = set()
    queue = [group_obj]
    while queue:
        cur = queue.pop(0)
        gname = _safe_text(getattr(cur, "Name", ""))
        if gname:
            if gname in seen:
                continue
            seen.add(gname)
        for child in (getattr(cur, "Group", []) or []):
            if _is_group(child):
                queue.append(child)
                continue
            try:
                k = _safe_text(getattr(child, "AutoRouteKey", "")).strip()
                if k:
                    keys.add(k)
            except Exception:
                pass
    return keys


def _delete_autoroute_objects(doc, group_obj):
    if doc is None or group_obj is None:
        return 0
    def _is_target_route(obj):
        if obj is None:
            return False
        key = _safe_text(getattr(obj, "AutoRouteKey", "")).strip()
        if not key:
            return False
        return True
    names = []
    seen = set()
    queue = [group_obj]
    while queue:
        cur = queue.pop(0)
        gname = _safe_text(getattr(cur, "Name", "")).strip()
        if gname:
            if gname in seen:
                continue
            seen.add(gname)
        for child in (getattr(cur, "Group", []) or []):
            if _is_group(child):
                queue.append(child)
                continue
            name = _safe_text(getattr(child, "Name", "")).strip()
            if _is_target_route(child) and name and name not in names:
                names.append(name)
    removed = 0
    for name in names:
        try:
            if doc.getObject(name) is not None:
                doc.removeObject(name)
                removed += 1
        except Exception:
            pass
    return removed


def _delete_autoroute_feeders(doc, group_obj, board_name):
    if doc is None or group_obj is None:
        return 0
    board_txt = _safe_text(board_name).strip()
    if not board_txt:
        return 0
    names = []
    seen = set()
    queue = [group_obj]
    while queue:
        cur = queue.pop(0)
        gname = _safe_text(getattr(cur, "Name", "")).strip()
        if gname:
            if gname in seen:
                continue
            seen.add(gname)
        for child in (getattr(cur, "Group", []) or []):
            if _is_group(child):
                queue.append(child)
                continue
            key = _safe_text(getattr(child, "AutoRouteKey", "")).strip()
            if not key:
                continue
            kind = _safe_text(getattr(child, "LinkKind", "")).strip().lower()
            oname = _safe_text(getattr(child, "OrigenName", "")).strip()
            dname = _safe_text(getattr(child, "DestinoName", "")).strip()
            is_feeder = (kind == "feeder") or (oname == board_txt) or (dname == board_txt)
            name = _safe_text(getattr(child, "Name", "")).strip()
            if is_feeder and name and name not in names:
                names.append(name)
    removed = 0
    for name in names:
        try:
            if doc.getObject(name) is not None:
                doc.removeObject(name)
                removed += 1
        except Exception:
            pass
    return removed


def _reserve_existing_ports(group_obj, used_ports):
    if group_obj is None:
        return
    seen = set()
    queue = [group_obj]
    while queue:
        cur = queue.pop(0)
        gname = _safe_text(getattr(cur, "Name", ""))
        if gname:
            if gname in seen:
                continue
            seen.add(gname)
        for child in (getattr(cur, "Group", []) or []):
            if _is_group(child):
                queue.append(child)
                continue
            oname = _safe_text(getattr(child, "OrigenName", "")).strip()
            dname = _safe_text(getattr(child, "DestinoName", "")).strip()
            oport = _safe_text(getattr(child, "PuertoOrigen", "")).strip()
            dport = _safe_text(getattr(child, "PuertoDestino", "")).strip()
            if oname and oport:
                used_ports.setdefault(oname, set()).add(oport)
            if dname and dport:
                used_ports.setdefault(dname, set()).add(dport)


def _migrate_autoroute_to_group(legacy_group, target_group):
    if legacy_group is None or target_group is None:
        return 0
    moved = 0
    seen = set()
    queue = [legacy_group]
    while queue:
        cur = queue.pop(0)
        gname = _safe_text(getattr(cur, "Name", ""))
        if gname:
            if gname in seen:
                continue
            seen.add(gname)
        children = list(getattr(cur, "Group", []) or [])
        for child in children:
            if _is_group(child):
                queue.append(child)
                continue
            key = _safe_text(getattr(child, "AutoRouteKey", "")).strip()
            if not key:
                continue
            try:
                if child not in (target_group.Group or []):
                    target_group.addObject(child)
                    moved += 1
            except Exception:
                pass
            # Intentar retirar del grupo legacy para dejar solo el nuevo arbol.
            try:
                if child in (cur.Group or []):
                    cur.removeObject(child)
            except Exception:
                pass
    return moved


def _device_order_key(obj):
    label = _safe_text(getattr(obj, "Label", "")) or _safe_text(getattr(obj, "Name", ""))
    parts = re.split(r"(\d+)", label.lower())
    key = []
    for p in parts:
        if p.isdigit():
            key.append(int(p))
        else:
            key.append(p)
    return tuple(key)


def _nearest_obj(obj, candidates, use_xy=True, max_distance=None):
    p0 = _anchor_point(obj)
    best = None
    best_d = None
    for c in (candidates or []):
        if c is None or c is obj:
            continue
        pc = _anchor_point(c)
        if bool(use_xy):
            dx = float(p0.x) - float(pc.x)
            dy = float(p0.y) - float(pc.y)
            d = (dx * dx + dy * dy) ** 0.5
        else:
            d = p0.distanceToPoint(pc)
        if max_distance is not None and d > float(max_distance):
            continue
        if best is None or d < best_d:
            best = c
            best_d = d
    return best


def _order_boxes_by_perimeter(boxes, board_obj=None):
    uniq = []
    seen = set()
    for bx in (boxes or []):
        name = _safe_text(getattr(bx, "Name", "")).strip()
        if bx is None or not name or name in seen:
            continue
        seen.add(name)
        uniq.append(bx)
    if len(uniq) <= 2:
        return uniq

    pts = [_anchor_point(bx) for bx in uniq]
    rect = _expand_rect(_bbox_xy(pts), 0.0)
    if rect is None:
        return uniq
    _xmin, _xmax, _ymin, _ymax, _w, _h, L = _rect_params(rect)
    items = []
    for bx in uniq:
        p = _anchor_point(bx)
        near = _nearest_rect_edge_point(p, rect, 0.0)
        if near is None:
            continue
        q, edge = near
        s = _rect_point_to_s(q, edge, rect)
        items.append({
            "obj": bx,
            "s": float(s),
            "pt": p,
            "name": _safe_text(getattr(bx, "Label", "")) or _safe_text(getattr(bx, "Name", "")),
        })
    if len(items) <= 2:
        return [it["obj"] for it in items] if items else uniq

    items.sort(key=lambda it: (float(it["s"]), _natural_key(it["name"])))
    best_gap = -1.0
    best_idx = 0
    for i, cur in enumerate(items):
        nxt = items[(i + 1) % len(items)]
        s1 = float(cur["s"])
        s2 = float(nxt["s"])
        if i == (len(items) - 1):
            s2 += float(L)
        gap = s2 - s1
        if gap > best_gap:
            best_gap = gap
            best_idx = i

    ordered = items[best_idx + 1:] + items[:best_idx + 1]
    if board_obj is not None and len(ordered) >= 2:
        b = _anchor_point(board_obj)
        start_f = ordered[0]["pt"].distanceToPoint(b)
        end_f = ordered[-1]["pt"].distanceToPoint(b)
        forward = [it["obj"] for it in ordered]
        reverse = list(reversed(forward))
        if end_f < start_f:
            ordered_objs = reverse
        else:
            ordered_objs = forward
    else:
        ordered_objs = [it["obj"] for it in ordered]

    _debug(
        "Orden backbone cajas: " +
        " -> ".join(_safe_text(getattr(o, "Label", "")) or _safe_text(getattr(o, "Name", "")) for o in ordered_objs)
    )
    return ordered_objs


def _same_level(a_obj, b_obj, tolerance):
    pa = _anchor_point(a_obj)
    pb = _anchor_point(b_obj)
    return abs(float(pa.z) - float(pb.z)) <= max(0.0, float(tolerance))


def _circuit_id_for_group(group_obj):
    label = _safe_text(getattr(group_obj, "Label", "")).strip()
    name = _safe_text(getattr(group_obj, "Name", "")).strip()
    return label or name or "Sin_Circuito"


def _collect_circuit_objects(circuit_group, get_component_type, include_apagadores):
    allowed = {"Toma"}
    if include_apagadores:
        allowed.add("Apagador")

    devices = []
    boxes = []
    for obj in _iter_non_group_descendants(circuit_group, skip_conexiones=True):
        if obj is None:
            continue
        if _is_octagon_box(obj):
            boxes.append(obj)
            continue
        ctype = ""
        if callable(get_component_type):
            try:
                ctype = _safe_text(get_component_type(obj))
            except Exception:
                ctype = ""
        if not ctype:
            ctype = _fallback_component_type(obj)
        if ctype in allowed:
            devices.append(obj)

    devices = sorted(devices, key=_device_order_key)
    return devices, boxes


def _map_boxes_by_source(boxes):
    out = {}
    for box in (boxes or []):
        key = _safe_text(getattr(box, "CajaOrigenKey", "")).strip()
        if not key:
            name = _safe_text(getattr(box, "CajaOrigenName", "")).strip()
            if name:
                key = f"NAME:{name}"
        if key and key not in out:
            out[key] = box
    return out


def _ensure_in_group(group_obj, obj):
    if group_obj is None or obj is None:
        return
    try:
        if obj not in (group_obj.Group or []):
            group_obj.addObject(obj)
    except Exception:
        pass


def _lane_offset_vector(lane_index, lane_count, separation, axis):
    sep = max(0.0, float(separation))
    n = max(1, int(lane_count))
    i = int(lane_index)
    centered = (float(i) - 0.5 * float(n - 1)) * sep
    max_abs = float(MAX_FEEDER_SPREAD_MM)
    if centered > max_abs:
        centered = max_abs
    elif centered < -max_abs:
        centered = -max_abs
    axis_txt = _safe_text(axis).strip().lower()
    if axis_txt.startswith("v"):
        return _vec(0.0, centered, 0.0)
    return _vec(centered, 0.0, 0.0)


def _tangent_coord_for_face(point, face):
    if point is None:
        return 0.0
    face_txt = _safe_text(face).strip()
    if face_txt in ("East", "West"):
        return float(point.y)
    return float(point.x)


def _feeder_sort_coord_for_face(face, coord):
    val = float(coord)
    face_txt = _safe_text(face).strip()
    if face_txt == "North":
        return -val
    return val


def _feeder_source_from_plan(plan):
    for src_obj, _dst_obj, link_kind in (plan or []):
        if _safe_text(link_kind).strip().lower() == "feeder":
            return src_obj
    return None


def _feeder_board_distance(src_pt, board_pt, guide_info=None):
    if src_pt is None or board_pt is None:
        return 0.0
    if guide_info is not None:
        src_proj = guide_info.get("src_proj")
        dst_proj = guide_info.get("dst_proj")
        if src_proj is not None and dst_proj is not None:
            try:
                return abs(float(dst_proj.get("s", 0.0)) - float(src_proj.get("s", 0.0)))
            except Exception:
                pass
    return _distance_xy(src_pt, board_pt)


def _feeder_lane_map(jobs, board_obj, guide_objs, cfg):
    items = []
    forced_face = _safe_text(cfg.get("anchor_face", "Auto")).strip() or "Auto"
    allowed_faces = _anchor_allowed_faces(cfg)
    face_rank = {"West": 0, "East": 1, "South": 2, "North": 3, "Top": 4, "Bottom": 5}
    manual_rank = _manual_circuit_rank_map(cfg)
    manual_guide_rank = {
        _safe_text(sec).strip(): idx
        for idx, sec in enumerate(cfg.get("manual_guide_order", []) or [])
        if _safe_text(sec).strip()
    } if bool(cfg.get("manual_guide_order_enabled", False)) else {}
    manual_section_order_map = dict(cfg.get("manual_section_circuit_order_map", {}) or {}) if bool(cfg.get("manual_section_circuit_order_enabled", False)) else {}
    manual_section_override_map = dict(cfg.get("manual_section_override_map", {}) or {})

    for job in (jobs or []):
        src_obj = _feeder_source_from_plan(job.get("plan"))
        if src_obj is None or board_obj is None:
            continue
        job_key = _safe_text(job.get("job_key", "")).strip()
        forced_section = _safe_text(manual_section_override_map.get(job_key, "")).strip()
        src_pt = _anchor_point(src_obj)
        face = _resolve_anchor_face(board_obj, toward_point=src_pt, forced_face=forced_face, allowed_faces=allowed_faces)
        board_ep = _board_face_endpoint(
            board_obj,
            toward_point=src_pt,
            forced_face=forced_face,
            tangent_offset=0.0,
            allowed_faces=allowed_faces,
        )
        guide_candidates = _guide_candidates_for_section(guide_objs, forced_section)
        guide_info = _best_guide_for_pair(
            src_pt,
            board_ep.get("point"),
            guide_candidates,
            offset_vec=_vec(0.0, 0.0, 0.0),
            offset_scalar=0.0,
            prefer_start=True,
        ) if guide_candidates else None
        guide_name = _safe_text(getattr(guide_info.get("obj"), "Name", "")) if guide_info else ""
        group_coord = _tangent_coord_for_face(board_ep.get("point"), face)
        source_coord = _tangent_coord_for_face(src_pt, face)
        if guide_info is not None:
            board_proj = _project_point_to_polyline_xy(board_ep.get("point"), guide_info.get("points", []))
            src_proj = guide_info.get("src_proj")
            if board_proj is not None:
                group_coord = _tangent_coord_for_face(board_proj.get("point"), face)
            if src_proj is not None:
                source_coord = _tangent_coord_for_face(src_proj.get("point"), face)
            if board_proj is not None:
                guide_info = dict(guide_info)
                guide_info["dst_proj"] = board_proj
        board_distance = _feeder_board_distance(src_pt, board_ep.get("point"), guide_info=guide_info)
        section_key = forced_section or guide_name or "AUTO"
        items.append({
            "job_key": job_key,
            "label": _safe_text(job.get("circuit_id", "")),
            "face": face,
            "guide": guide_name,
            "forced_section": forced_section,
            "section_key": section_key,
            "group_coord": float(group_coord),
            "source_coord": float(source_coord),
            "board_distance": float(board_distance),
            "board_x": float(getattr(board_ep.get("point"), "x", 0.0)),
            "board_y": float(getattr(board_ep.get("point"), "y", 0.0)),
        })

    if not items:
        return {}, 0, {}

    def _section_sort_value(face_txt, section_items):
        vals = [
            _feeder_sort_coord_for_face(face_txt, it.get("group_coord", it.get("source_coord", 0.0)))
            for it in (section_items or [])
        ]
        if not vals:
            return 0.0
        return sum(float(v) for v in vals) / float(len(vals))

    def _section_sort_key(face_txt, sec_key, sec_items):
        key_txt = _safe_text(sec_key)
        guide_order = int(manual_guide_rank.get(key_txt, 10 ** 8))
        auto_rank = 1 if key_txt == "AUTO" else 0
        return (
            guide_order,
            auto_rank,
            _section_sort_value(face_txt, sec_items),
            key_txt,
        )

    def _ordered_section_items(face_txt, sec_key, sec_items, for_plan=False):
        sec_txt = _safe_text(sec_key)
        sec_manual = {
            _safe_text(job_key).strip(): idx
            for idx, job_key in enumerate(manual_section_order_map.get(sec_txt, []) or [])
            if _safe_text(job_key).strip()
        }
        return sorted(
            list(sec_items),
            key=lambda it: (
                int(sec_manual.get(_safe_text(it.get("job_key", "")), 10 ** 8)),
                int(manual_rank.get(_safe_text(it.get("job_key", "")), 10 ** 9)),
                (_feeder_sort_coord_for_face(face_txt, it.get("source_coord", 0.0))),
                (-float(it.get("board_distance", 0.0)) if for_plan else 0.0),
                _natural_key(it.get("label", "")),
            ),
        )

    def _ordered_face_items(face_txt, face_items, for_plan=False):
        by_section = defaultdict(list)
        for it in (face_items or []):
            by_section[_safe_text(it.get("section_key", ""))].append(it)
        ordered = []
        for sec_key, sec_items in sorted(
            by_section.items(),
            key=lambda pair: _section_sort_key(face_txt, pair[0], pair[1]),
        ):
            ordered_sec = _ordered_section_items(face_txt, sec_key, sec_items, for_plan=for_plan)
            ordered.extend(ordered_sec)
        return ordered

    items_by_face = defaultdict(list)
    for it in items:
        items_by_face[_safe_text(it.get("face"))].append(it)

    plan_items = []
    for face_txt, face_items in sorted(items_by_face.items(), key=lambda pair: face_rank.get(_safe_text(pair[0]), 99)):
        plan_items.extend(_ordered_face_items(face_txt, face_items, for_plan=True))
    lane_map = {it["job_key"]: idx for idx, it in enumerate(plan_items)}
    lane_meta = {}
    for face_txt, face_items in items_by_face.items():
        by_section = defaultdict(list)
        for it in face_items:
            by_section[_safe_text(it.get("section_key", ""))].append(it)
        _debug(
            "Secciones tablero "
            f"{face_txt}: " +
            " ".join(
                f"[sec={sec_key or '-'} coord={_section_sort_value(face_txt, sec_items):.1f} n={len(sec_items)}]"
                for sec_key, sec_items in sorted(
                    by_section.items(),
                    key=lambda pair: _section_sort_key(face_txt, pair[0], pair[1]),
                )
            )
        )
        ordered_sections = sorted(
            by_section.items(),
            key=lambda pair: _section_sort_key(face_txt, pair[0], pair[1]),
        )
        board_items = []
        section_count = max(1, len(ordered_sections))
        for sec_idx, (sec_key, sec_items) in enumerate(ordered_sections):
            ordered_sec = _ordered_section_items(face_txt, sec_key, sec_items, for_plan=False)
            board_items.extend(ordered_sec)
            for sec_lane_idx, it in enumerate(ordered_sec):
                plan_idx = lane_map.get(it["job_key"], sec_lane_idx)
                lane_meta[it["job_key"]] = {
                    "face": face_txt,
                    "face_index": int(len(board_items) - len(ordered_sec) + sec_lane_idx),
                    "face_count": int(len(face_items)),
                    "route_index": int(len(board_items) - len(ordered_sec) + sec_lane_idx),
                    "route_count": int(len(face_items)),
                    "plan_order": int(plan_idx),
                    "board_distance": float(it.get("board_distance", 0.0)),
                    "section_key": _safe_text(it.get("section_key", "")).strip(),
                    "section_index": int(sec_idx),
                    "section_count": int(section_count),
                    "section_lane_index": int(sec_lane_idx),
                    "section_lane_count": int(len(ordered_sec)),
                }
        _debug(
            "Orden salidas tablero "
            f"{face_txt}: " +
            " -> ".join(
                f"{_safe_text(it.get('label', ''))}"
                f"[sec={_safe_text(it.get('section_key', '')) or '-'}"
                f",src={float(it.get('source_coord', 0.0)):.1f}"
                f",board=({float(it.get('board_x', 0.0)):.1f},{float(it.get('board_y', 0.0)):.1f})]"
                for it in board_items
            )
        )
    _debug(
        "Orden alimentadores: " +
        " | ".join(
            f"{it['label']} face={it['face']} guia={it['guide'] or '-'} "
            f"sec={it['section_key'] or '-'} group={it['group_coord']:.1f} src={it['source_coord']:.1f} "
            f"board=({float(it.get('board_x', 0.0)):.1f},{float(it.get('board_y', 0.0)):.1f}) "
            f"dist={float(it.get('board_distance', 0.0)):.1f} "
            f"lane={lane_map[it['job_key']]} face_lane={lane_meta[it['job_key']]['face_index']}/{lane_meta[it['job_key']]['face_count']} "
            f"sec_lane={lane_meta[it['job_key']].get('section_lane_index', 0)}/{lane_meta[it['job_key']].get('section_lane_count', 1)} "
            f"sec_block={lane_meta[it['job_key']].get('section_index', 0)}/{lane_meta[it['job_key']].get('section_count', 1)}"
            for it in plan_items
        )
    )
    return lane_map, len(items), lane_meta


def _route_reference_points(obj, anchor_face="Auto", anchor_faces=None):
    pts = []
    if obj is None:
        return pts
    if _is_board_like(obj):
        face = _safe_text(anchor_face).strip()
        ep = None
        if face in BOARD_FACES:
            ep = _board_face_endpoint(obj, toward_point=None, forced_face=face, tangent_offset=0.0, allowed_faces=anchor_faces)
        elif anchor_faces:
            ep = _board_face_endpoint(obj, toward_point=None, forced_face="Auto", tangent_offset=0.0, allowed_faces=anchor_faces)
        if ep is not None and ep.get("point") is not None:
            pts.append(ep["point"])
            return pts
    if _is_octagon_box(obj):
        ports = _world_ports(obj)
        for p in (ports or []):
            name = _safe_text(p.get("name", "")).strip()
            if not name or name == "Bottom":
                continue
            pt = p.get("point")
            if pt is not None:
                pts.append(pt)
    if not pts:
        pts.append(_anchor_point(obj))
    return pts


def _route_rect_for_circuit(devices, boxes, cfg, board_obj=None, use_box_ports=False):
    pts = []
    for o in (boxes or []):
        if use_box_ports:
            pts.extend(_route_reference_points(o))
        else:
            pts.append(_anchor_point(o))
    for o in (devices or []):
        pts.extend(_route_reference_points(o))
    if board_obj is not None:
        pts.extend(
            _route_reference_points(
                board_obj,
                anchor_face=_safe_text(cfg.get("anchor_face", "Auto")),
                anchor_faces=_anchor_allowed_faces(cfg),
            )
        )
    rect = _bbox_xy(pts)
    if rect is None:
        return None
    margin = float(cfg.get("wall_margin", DEFAULT_WALL_OFFSET))
    return _expand_rect(rect, margin)


def _preferred_backbone_port_pair(src_obj, dst_obj):
    if not (_is_octagon_box(src_obj) and _is_octagon_box(dst_obj)):
        return None
    p1 = _anchor_point(src_obj)
    p2 = _anchor_point(dst_obj)
    dx = float(p2.x) - float(p1.x)
    dy = float(p2.y) - float(p1.y)
    if abs(dx) <= EPS and abs(dy) <= EPS:
        return None

    if abs(dx) <= EPS:
        src_name = "North" if dy >= 0.0 else "South"
        dst_name = "South" if dy >= 0.0 else "North"
        return {"src": (src_name,), "dst": (dst_name,), "final_axis": "y"}
    if abs(dy) <= EPS:
        src_name = "East" if dx >= 0.0 else "West"
        dst_name = "West" if dx >= 0.0 else "East"
        return {"src": (src_name,), "dst": (dst_name,), "final_axis": "x"}

    # Regla estable: usar el eje dominante para ambos extremos.
    # Esto evita combinaciones cruzadas (ej. East -> North) que suelen generar
    # sobrepaso y retorno en la llegada.
    if abs(dx) >= abs(dy):
        src_name = "East" if dx >= 0.0 else "West"
        dst_name = "West" if dx >= 0.0 else "East"
        return {"src": (src_name,), "dst": (dst_name,), "final_axis": "x"}

    src_name = "North" if dy >= 0.0 else "South"
    dst_name = "South" if dy >= 0.0 else "North"
    return {"src": (src_name,), "dst": (dst_name,), "final_axis": "y"}


def _preferred_ports_for_link_end(end_obj, other_obj, link_kind, toward_point=None):
    if not _is_octagon_box(end_obj):
        return None
    kind = _safe_text(link_kind).strip().lower()
    patch_active = bool(globals().get("RAMAL_LUZ_PATCH_ACTIVE", False))
    use_all_sides = bool(patch_active and ALLOW_DIAGONAL_PORTS_FOR_SWITCH_BOXES and _is_switch_origin_box(end_obj))
    if kind in ("drop_box", "drop_nearest") and _is_luminaria_like(other_obj):
        if toward_point is not None:
            return _ordered_all_side_ports(end_obj, toward_point, include_diagonal=True)
        return ("North", "East", "South", "West", "NorthEast", "NorthWest", "SouthEast", "SouthWest")
    if use_all_sides:
        if toward_point is not None:
            return _ordered_all_side_ports(end_obj, toward_point, include_diagonal=True)
        return ("North", "East", "South", "West", "NorthEast", "NorthWest", "SouthEast", "SouthWest")
    if toward_point is not None:
        return _ordered_cardinal_ports(end_obj, toward_point)
    return CARDINAL_PORTS


def _strict_cardinal_for_link_end(end_obj, other_obj, link_kind):
    if not STRICT_BACKBONE_CARDINAL:
        return False
    patch_active = bool(globals().get("RAMAL_LUZ_PATCH_ACTIVE", False))
    if patch_active and ALLOW_DIAGONAL_PORTS_FOR_SWITCH_BOXES and _is_switch_origin_box(end_obj):
        return False
    if patch_active and _safe_text(link_kind).strip().lower() in ("drop_box", "drop_nearest") and _is_luminaria_like(other_obj):
        return False
    if _safe_text(link_kind).strip().lower() == "drop_box":
        return _is_octagon_box(end_obj)
    return _is_octagon_box(end_obj)


def _effective_route_z_for_link(src_obj, dst_obj, link_kind, default_route_z):
    kind = _safe_text(link_kind).strip().lower()
    if kind == "drop_nearest" and (not _is_octagon_box(src_obj)) and (not _is_octagon_box(dst_obj)):
        p1 = _anchor_point(src_obj)
        p2 = _anchor_point(dst_obj)
        return max(float(p1.z), float(p2.z))
    return float(default_route_z)


def _connect_pair(
    doc,
    src_obj,
    dst_obj,
    circuit_id,
    conduit_type,
    diameter,
    bend_radius,
    route_z,
    orthogonal_route,
    route_by_perimeter,
    route_rect,
    guide_objs,
    guide_section_key,
    link_kind,
    board_obj,
    anchor_face,
    anchor_faces,
    feeder_lane_vec,
    feeder_board_lane_index,
    feeder_board_lane_count,
    feeder_board_lane_separation,
    feeder_board_section_index,
    feeder_board_section_count,
    feeder_board_section_lane_index,
    feeder_board_section_lane_count,
    reserve_ports,
    used_ports,
    group_target,
    existing_keys,
    skip_existing,
):
    if src_obj is None or dst_obj is None or src_obj is dst_obj:
        return "skip", None
    patch_active = bool(globals().get("RAMAL_LUZ_PATCH_ACTIVE", False))

    board_name = _safe_text(getattr(board_obj, "Name", ""))
    src_name = _safe_text(getattr(src_obj, "Name", ""))
    dst_name = _safe_text(getattr(dst_obj, "Name", ""))
    src_label = _safe_text(getattr(src_obj, "Label", "")) or src_name
    dst_label = _safe_text(getattr(dst_obj, "Label", "")) or dst_name
    is_src_board = bool(board_name) and (src_name == board_name or src_obj is board_obj)
    is_dst_board = bool(board_name) and (dst_name == board_name or dst_obj is board_obj)
    lane_vec = feeder_lane_vec if feeder_lane_vec is not None else _vec(0.0, 0.0, 0.0)
    lane_scalar = float(lane_vec.x) if abs(float(lane_vec.x)) >= abs(float(lane_vec.y)) else float(lane_vec.y)
    is_feeder = _safe_text(link_kind).strip().lower() == "feeder"
    keep_offset_board_entry = bool(is_feeder and _vlen(lane_vec) > EPS)
    guide_entry_axis = "x" if abs(float(lane_vec.x)) >= abs(float(lane_vec.y)) else "y"
    anchor_face_txt = _safe_text(anchor_face).strip() or "Auto"
    anchor_allowed_faces = [x for x in (anchor_faces or list(BOARD_FACES)) if _safe_text(x).strip() in BOARD_FACES]
    board_lane_index = max(0, int(feeder_board_lane_index))
    board_lane_count = max(1, int(feeder_board_lane_count))
    board_lane_sep = max(0.0, float(feeder_board_lane_separation))
    board_section_index = max(0, int(feeder_board_section_index))
    board_section_count = max(1, int(feeder_board_section_count))
    board_section_lane_index = max(0, int(feeder_board_section_lane_index))
    board_section_lane_count = max(1, int(feeder_board_section_lane_count))
    tangent_scalar = _board_tangent_offset(_resolve_anchor_face(board_obj, toward_point=_anchor_point(src_obj), forced_face=anchor_face_txt, allowed_faces=anchor_allowed_faces), lane_scalar) if (is_feeder and board_obj is not None) else 0.0

    hint_src_point = _anchor_point(src_obj)
    hint_dst_point = _anchor_point(dst_obj)
    if is_feeder and _vlen(lane_vec) > EPS:
        if is_src_board and not _is_board_like(src_obj):
            hint_src_point = _vec(hint_src_point.x + lane_vec.x, hint_src_point.y + lane_vec.y, hint_src_point.z)
        if is_dst_board and not _is_board_like(dst_obj):
            hint_dst_point = _vec(hint_dst_point.x + lane_vec.x, hint_dst_point.y + lane_vec.y, hint_dst_point.z)
    if is_src_board and _is_board_like(src_obj):
        hint_src_point = _board_face_endpoint(
            src_obj,
            toward_point=hint_dst_point,
            forced_face=anchor_face_txt,
            tangent_offset=tangent_scalar,
            allowed_faces=anchor_allowed_faces,
            lane_index=board_lane_index,
            lane_count=board_lane_count,
            lane_separation=board_lane_sep,
            section_index=board_section_index,
            section_count=board_section_count,
            section_lane_index=board_section_lane_index,
            section_lane_count=board_section_lane_count,
        )["point"]
    if is_dst_board and _is_board_like(dst_obj):
        hint_dst_point = _board_face_endpoint(
            dst_obj,
            toward_point=hint_src_point,
            forced_face=anchor_face_txt,
            tangent_offset=tangent_scalar,
            allowed_faces=anchor_allowed_faces,
            lane_index=board_lane_index,
            lane_count=board_lane_count,
            lane_separation=board_lane_sep,
            section_index=board_section_index,
            section_count=board_section_count,
            section_lane_index=board_section_lane_index,
            section_lane_count=board_section_lane_count,
        )["point"]
    guide_offset = lane_vec if is_feeder and _vlen(lane_vec) > EPS else _vec(0.0, 0.0, 0.0)
    guide_candidates = _guide_candidates_for_section(guide_objs, guide_section_key) if is_feeder else list(guide_objs or [])
    guide_hint = _best_guide_for_pair(
        hint_src_point,
        hint_dst_point,
        guide_candidates,
        offset_vec=_vec(0.0, 0.0, 0.0),
        offset_scalar=lane_scalar,
        prefer_start=True,
    ) if is_feeder and guide_candidates else None
    kind_txt = _safe_text(link_kind).strip().lower()
    use_backbone_perimeter = bool(route_by_perimeter) and kind_txt == "backbone" and route_rect is not None
    is_trunk_link = kind_txt in ("backbone", "switch_backbone", "feeder")
    backbone_pair = _preferred_backbone_port_pair(src_obj, dst_obj) if is_trunk_link and not use_backbone_perimeter else None

    src_hint = _anchor_point(dst_obj)
    dst_hint = _anchor_point(src_obj)
    if is_feeder and _vlen(lane_vec) > EPS and board_obj is not None:
        b = _anchor_point(board_obj)
        board_hint = _vec(b.x + lane_vec.x, b.y + lane_vec.y, b.z)
        if is_src_board:
            dst_hint = board_hint
        if is_dst_board:
            src_hint = board_hint
    if is_src_board and _is_board_like(src_obj):
        src_hint = _board_face_endpoint(
            src_obj,
            toward_point=dst_hint,
            forced_face=anchor_face_txt,
            tangent_offset=tangent_scalar,
            allowed_faces=anchor_allowed_faces,
            lane_index=board_lane_index,
            lane_count=board_lane_count,
            lane_separation=board_lane_sep,
            section_index=board_section_index,
            section_count=board_section_count,
            section_lane_index=board_section_lane_index,
            section_lane_count=board_section_lane_count,
        )["point"]
    if is_dst_board and _is_board_like(dst_obj):
        dst_hint = _board_face_endpoint(
            dst_obj,
            toward_point=src_hint,
            forced_face=anchor_face_txt,
            tangent_offset=tangent_scalar,
            allowed_faces=anchor_allowed_faces,
            lane_index=board_lane_index,
            lane_count=board_lane_count,
            lane_separation=board_lane_sep,
            section_index=board_section_index,
            section_count=board_section_count,
            section_lane_index=board_section_lane_index,
            section_lane_count=board_section_lane_count,
        )["point"]
    if guide_hint is not None:
        if _is_octagon_box(src_obj):
            gp = _guide_hint_point_for_endpoint(guide_hint, "src", _anchor_point(src_obj).z)
            if gp is not None:
                src_hint = gp
        if _is_octagon_box(dst_obj):
            gp = _guide_hint_point_for_endpoint(guide_hint, "dst", _anchor_point(dst_obj).z)
            if gp is not None:
                dst_hint = gp

    if use_backbone_perimeter:
        ep_src = {"point": _anchor_point(src_obj), "port": "", "dir": _vec(0.0, 0.0, 0.0)}
        ep_dst = {"point": _anchor_point(dst_obj), "port": "", "dir": _vec(0.0, 0.0, 0.0)}
    else:
        src_pref_ports = (
            backbone_pair.get("src")
            if backbone_pair is not None
            else _preferred_ports_for_link_end(src_obj, dst_obj, link_kind, toward_point=src_hint)
        )
        dst_pref_ports = (
            backbone_pair.get("dst")
            if backbone_pair is not None
            else _preferred_ports_for_link_end(dst_obj, src_obj, link_kind, toward_point=dst_hint)
        )
        src_strict = _strict_cardinal_for_link_end(src_obj, dst_obj, link_kind)
        dst_strict = _strict_cardinal_for_link_end(dst_obj, src_obj, link_kind)
        avoid_reuse_src = _is_octagon_box(src_obj) and (kind_txt in ("drop_box", "drop_nearest"))
        avoid_reuse_dst = _is_octagon_box(dst_obj) and (kind_txt in ("drop_box", "drop_nearest"))
        if is_src_board and _is_board_like(src_obj):
            ep_src = _board_face_endpoint(
                src_obj,
                toward_point=src_hint,
                forced_face=anchor_face_txt,
                tangent_offset=tangent_scalar,
                allowed_faces=anchor_allowed_faces,
                lane_index=board_lane_index,
                lane_count=board_lane_count,
                lane_separation=board_lane_sep,
                section_index=board_section_index,
                section_count=board_section_count,
                section_lane_index=board_section_lane_index,
                section_lane_count=board_section_lane_count,
            )
        else:
            ep_src = _select_endpoint(
                src_obj,
                src_hint,
                used_ports,
                reserve_ports=reserve_ports,
                prefer_port_names=src_pref_ports,
                strict_preferred=src_strict,
                avoid_reuse=avoid_reuse_src,
            )
        if is_dst_board and _is_board_like(dst_obj):
            ep_dst = _board_face_endpoint(
                dst_obj,
                toward_point=dst_hint,
                forced_face=anchor_face_txt,
                tangent_offset=tangent_scalar,
                allowed_faces=anchor_allowed_faces,
                lane_index=board_lane_index,
                lane_count=board_lane_count,
                lane_separation=board_lane_sep,
                section_index=board_section_index,
                section_count=board_section_count,
                section_lane_index=board_section_lane_index,
                section_lane_count=board_section_lane_count,
            )
        else:
            ep_dst = _select_endpoint(
                dst_obj,
                dst_hint,
                used_ports,
                reserve_ports=reserve_ports,
                prefer_port_names=dst_pref_ports,
                strict_preferred=dst_strict,
                avoid_reuse=avoid_reuse_dst,
            )

    p1 = ep_src["point"]
    p2 = ep_dst["point"]
    active_route_z = _effective_route_z_for_link(src_obj, dst_obj, link_kind, route_z)
    _debug(
        f"{_safe_text(link_kind)} | {_safe_text(circuit_id)} | "
        f"{src_label}:{_safe_text(ep_src.get('port', ''))} -> {dst_label}:{_safe_text(ep_dst.get('port', ''))} | "
        f"src={_fmt_vec(p1)} dir={_fmt_vec(ep_src.get('dir'))} | "
        f"dst={_fmt_vec(p2)} dir={_fmt_vec(ep_dst.get('dir'))} | route_z={float(active_route_z):.1f} "
        f"perim_backbone={'SI' if use_backbone_perimeter else 'NO'} "
        f"board_lane={board_lane_index}/{board_lane_count}"
    )
    if p1.distanceToPoint(p2) <= 0.1:
        _debug("Conexion omitida: puntos origen/destino coinciden.")
        return "skip", None

    route_key = _connection_key(circuit_id, src_obj, dst_obj, ep_src.get("port", ""), ep_dst.get("port", ""))
    if skip_existing and route_key in existing_keys:
        _debug(f"Conexion existente omitida: {route_key}")
        return "existing", route_key

    stub_len = max(40.0, min(float(bend_radius), float(DEFAULT_PORT_STUB)))
    src_dir = _normalize(ep_src.get("dir", _vec(0.0, 0.0, 0.0)))
    dst_dir = _normalize(ep_dst.get("dir", _vec(0.0, 0.0, 0.0)))
    stub_src = None
    stub_dst = None
    src_port_name = _safe_text(ep_src.get("port", "")).strip()
    dst_port_name = _safe_text(ep_dst.get("port", "")).strip()

    src_to_other = _normalize(_vec(float(p2.x) - float(p1.x), float(p2.y) - float(p1.y), 0.0))
    dst_to_other = _normalize(_vec(float(p1.x) - float(p2.x), float(p1.y) - float(p2.y), 0.0))
    src_align = _dot(src_dir, src_to_other) if (_vlen(src_dir) > EPS and _vlen(src_to_other) > EPS) else 0.0
    dst_align = _dot(dst_dir, dst_to_other) if (_vlen(dst_dir) > EPS and _vlen(dst_to_other) > EPS) else 0.0
    align_min = 0.35

    allow_src_stub = (
        _is_octagon_box(src_obj)
        and _vlen(src_dir) > EPS
        and src_port_name != "Bottom"
        and kind_txt != "drop_box"
        and ((not is_trunk_link) if patch_active else True)
        and not use_backbone_perimeter
        and src_align >= align_min
    )
    allow_dst_stub = (
        _is_octagon_box(dst_obj)
        and _vlen(dst_dir) > EPS
        and dst_port_name != "Bottom"
        and kind_txt != "drop_box"
        and ((not is_trunk_link) if patch_active else True)
        and not use_backbone_perimeter
        and dst_align >= align_min
    )
    if allow_src_stub:
        stub_src = _vec(p1.x + (src_dir.x * stub_len), p1.y + (src_dir.y * stub_len), p1.z)
    if allow_dst_stub:
        stub_dst = _vec(p2.x + (dst_dir.x * stub_len), p2.y + (dst_dir.y * stub_len), p2.z)

    rp1 = _vec((stub_src.x if stub_src is not None else p1.x), (stub_src.y if stub_src is not None else p1.y), (stub_src.z if stub_src is not None else p1.z))
    rp2 = _vec((stub_dst.x if stub_dst is not None else p2.x), (stub_dst.y if stub_dst is not None else p2.y), (stub_dst.z if stub_dst is not None else p2.z))
    if is_feeder and _vlen(lane_vec) > EPS:
        if is_src_board and not _is_board_like(src_obj):
            rp1 = _vec(p1.x + lane_vec.x, p1.y + lane_vec.y, p1.z)
        if is_dst_board and not _is_board_like(dst_obj):
            rp2 = _vec(p2.x + lane_vec.x, p2.y + lane_vec.y, p2.z)

    guide_route = _best_guide_for_pair(
        rp1,
        rp2,
        guide_candidates,
        offset_vec=_vec(0.0, 0.0, 0.0),
        offset_scalar=lane_scalar,
        prefer_start=True,
    ) if is_feeder and guide_candidates else None
    final_axis = backbone_pair.get("final_axis") if backbone_pair is not None else None
    if final_axis is None and _vlen(dst_dir) > EPS:
        final_axis = "x" if abs(float(dst_dir.x)) >= abs(float(dst_dir.y)) else "y"
    if is_feeder and guide_route is not None:
        dst_face_txt = _safe_text(ep_dst.get("port", "")).strip()
        if is_dst_board and dst_face_txt in ("Top", "Bottom"):
            final_axis = "y"

    pts = _route_points(
        rp1,
        rp2,
        z_level=active_route_z,
        orthogonal=orthogonal_route,
        route_by_perimeter=route_by_perimeter,
        rect=route_rect,
        guide_info=guide_route,
        final_axis=final_axis,
        src_port=ep_src.get("port", ""),
        dst_port=ep_dst.get("port", ""),
        entry_axis=(guide_entry_axis if is_feeder and guide_route is not None else None),
    )
    if patch_active and is_trunk_link and (not use_backbone_perimeter) and pts:
        escape_len = max(18.0, min(float(bend_radius) * 0.45, 42.0))
        rp1_fix = rp1
        rp2_fix = rp2
        reroute = False
        src_cross = (
            _is_octagon_box(src_obj)
            and (not is_src_board)
            and _vlen(src_dir) > EPS
            and src_port_name != "Bottom"
            and _route_crosses_box_interior_xy(src_obj, pts, margin=1.0)
        )
        dst_cross = (
            _is_octagon_box(dst_obj)
            and (not is_dst_board)
            and _vlen(dst_dir) > EPS
            and dst_port_name != "Bottom"
            and _route_crosses_box_interior_xy(dst_obj, pts, margin=1.0)
        )
        if src_cross:
            rp1_fix = _vec(
                float(p1.x) + (float(src_dir.x) * escape_len),
                float(p1.y) + (float(src_dir.y) * escape_len),
                float(p1.z),
            )
            reroute = True
        if dst_cross:
            rp2_fix = _vec(
                float(p2.x) + (float(dst_dir.x) * escape_len),
                float(p2.y) + (float(dst_dir.y) * escape_len),
                float(p2.z),
            )
            reroute = True
        if reroute:
            pts = _route_points(
                rp1_fix,
                rp2_fix,
                z_level=active_route_z,
                orthogonal=orthogonal_route,
                route_by_perimeter=route_by_perimeter,
                rect=route_rect,
                guide_info=guide_route,
                final_axis=final_axis,
                src_port=ep_src.get("port", ""),
                dst_port=ep_dst.get("port", ""),
                entry_axis=(guide_entry_axis if is_feeder and guide_route is not None else None),
            )
            if rp1_fix.distanceToPoint(p1) > 0.1:
                pts = _dedup_points([p1] + list(pts or []))
            if rp2_fix.distanceToPoint(p2) > 0.1:
                pts = _dedup_points(list(pts or []) + [p2])
            _debug(
                f"Ajuste anti-atravesar caja | src_cross={'SI' if src_cross else 'NO'} "
                f"dst_cross={'SI' if dst_cross else 'NO'} "
                f"rp1_fix={_fmt_vec(rp1_fix)} rp2_fix={_fmt_vec(rp2_fix)} "
                f"pts={_fmt_points(pts)}"
            )
    if use_backbone_perimeter and len(pts) >= 2:
        src_trim_ep = _reserve_perimeter_box_endpoint(src_obj, pts[1], used_ports, reserve_ports=reserve_ports)
        dst_trim_ep = _reserve_perimeter_box_endpoint(dst_obj, pts[-2], used_ports, reserve_ports=reserve_ports)
        src_trim = src_trim_ep.get("point")
        dst_trim = dst_trim_ep.get("point")
        if src_trim is not None:
            pts[0] = _vec(src_trim.x, src_trim.y, pts[0].z)
            ep_src["point"] = pts[0]
            ep_src["port"] = _safe_text(src_trim_ep.get("port", ""))
            ep_src["dir"] = src_trim_ep.get("dir", _vec(0.0, 0.0, 0.0))
        if dst_trim is not None:
            pts[-1] = _vec(dst_trim.x, dst_trim.y, pts[-1].z)
            ep_dst["point"] = pts[-1]
            ep_dst["port"] = _safe_text(dst_trim_ep.get("port", ""))
            ep_dst["dir"] = dst_trim_ep.get("dir", _vec(0.0, 0.0, 0.0))
        _debug(
            f"Perimetro a caja | src_trim={_fmt_vec(src_trim)} dst_trim={_fmt_vec(dst_trim)} "
            f"pts={_fmt_points(pts)}"
        )
    _debug(
        f"Ruta base | final_axis={_safe_text(final_axis) or '-'} "
        f"perimetro={'SI' if route_by_perimeter else 'NO'} guia={'SI' if guide_route is not None else 'NO'} "
        f"seccion={_safe_text(guide_section_key) or '-'} "
        f"entry_axis={guide_entry_axis if is_feeder and guide_route is not None else '-'} "
        f"lane={_fmt_vec(lane_vec)} lane_scalar={lane_scalar:.1f} "
        f"guia_obj={_safe_text(getattr(guide_route.get('obj'), 'Name', '')) if guide_route else '-'} "
        f"rp1={_fmt_vec(rp1)} rp2={_fmt_vec(rp2)} pts={_fmt_points(pts)}"
    )
    if is_src_board and (not keep_offset_board_entry) and rp1.distanceToPoint(p1) > 0.1 and pts:
        zs = max(float(active_route_z), float(p1.z), float(rp1.z))
        lead = _dedup_points([p1, _vec(p1.x, p1.y, zs), _vec(rp1.x, rp1.y, zs), rp1])
        pts = _dedup_points(lead + pts[1:])
    elif stub_src is not None and pts:
        pts = _dedup_points([p1, stub_src] + pts[1:])
    if is_dst_board and (not keep_offset_board_entry) and rp2.distanceToPoint(p2) > 0.1 and pts:
        ze = max(float(active_route_z), float(p2.z), float(rp2.z))
        tail = _dedup_points([pts[-1], _vec(pts[-1].x, pts[-1].y, ze), _vec(p2.x, p2.y, ze), p2])
        pts = _dedup_points(pts[:-1] + tail)
    elif stub_dst is not None and pts:
        pts = _dedup_points(pts[:-1] + [stub_dst, p2])
    pts_before = list(pts)
    pts = _simplify_orthogonal_points(pts)
    if patch_active:
        pts = _trim_endpoint_backtrack(pts)
    pts = _simplify_orthogonal_points(pts)
    if pts_before != pts:
        _debug(f"Ruta simplificada | antes={_fmt_points(pts_before)} | despues={_fmt_points(pts)}")
    if len(pts) < 2:
        _debug("Conexion omitida: menos de 2 puntos luego de simplificar.")
        return "skip", None

    wire = _make_wire(pts)
    circ_token = _safe_name_token(circuit_id, "Circuito")
    src_lab = src_label
    dst_lab = dst_label
    wire.Label = f"{conduit_type}_{circ_token}: {src_lab} -> {dst_lab}"

    _set_wire_metadata(
        wire=wire,
        conduit_type=conduit_type,
        diameter=diameter,
        bend_radius=bend_radius,
        circuit_id=circuit_id,
        src_obj=src_obj,
        dst_obj=dst_obj,
        src_port=ep_src.get("port", ""),
        dst_port=ep_dst.get("port", ""),
        link_kind=link_kind,
        route_key=route_key,
    )
    effective_radius = _effective_fillet_radius(pts, bend_radius)
    if effective_radius + 0.1 < float(bend_radius):
        _debug(
            f"Radio de curvatura ajustado {float(bend_radius):.1f} -> {float(effective_radius):.1f} mm "
            f"por segmentos cortos. puntos={_fmt_points(pts)}"
        )
    _style_wire(wire, conduit_type, bend_radius=effective_radius)
    _ensure_in_group(group_target, wire)
    existing_keys.add(route_key)
    _debug(f"Wire creada | key={route_key} | puntos={_fmt_points(pts)}")
    return "created", route_key


def _planned_pair_key(a_obj, b_obj):
    a = _safe_text(getattr(a_obj, "Name", ""))
    b = _safe_text(getattr(b_obj, "Name", ""))
    if not a or not b:
        return ""
    x, y = sorted([a, b])
    return f"{x}|{y}"


def _build_plan_for_circuit(circuit_group, devices, boxes, box_by_source, board_obj, cfg):
    plan = []
    seen_pairs = set()
    same_level_only = bool(cfg.get("direct_same_level_only", True))
    level_tol = max(0.0, float(cfg.get("device_level_tolerance", DEFAULT_DEVICE_LEVEL_TOLERANCE)))

    def push(a_obj, b_obj, kind):
        if a_obj is None or b_obj is None or a_obj is b_obj:
            return
        k = _planned_pair_key(a_obj, b_obj)
        if not k or k in seen_pairs:
            return
        seen_pairs.add(k)
        plan.append((a_obj, b_obj, _safe_text(kind)))

    # 1) Bajantes por dispositivo.
    missing = []
    devices_with_box = []
    for dev in devices:
        bx = box_by_source.get(_source_key(dev))
        if bx is not None:
            devices_with_box.append(dev)
            push(dev, bx, "drop_box")
        else:
            missing.append(dev)

    # 2) Fallback cuando no existe caja.
    if cfg.get("fallback_missing_box", True):
        near_limit = max(0.0, float(cfg.get("fallback_near_mm", DEFAULT_FALLBACK_NEAR_MM)))
        for dev in missing:
            preferred = [o for o in devices_with_box if o is not dev]
            others = [o for o in devices if o is not dev]
            preferred_same = [o for o in preferred if (not same_level_only) or _same_level(dev, o, level_tol)]
            others_same = [o for o in others if (not same_level_only) or _same_level(dev, o, level_tol)]

            near = _nearest_obj(dev, preferred_same, use_xy=True, max_distance=near_limit)
            if near is None:
                near = _nearest_obj(dev, others_same, use_xy=True, max_distance=near_limit)
            if near is None:
                near = _nearest_obj(dev, preferred_same, use_xy=True)
            if near is None:
                near = _nearest_obj(dev, others_same, use_xy=True)
            if near is not None:
                push(dev, near, "drop_nearest")
                continue

            candidate_boxes = [box_by_source.get(_source_key(o)) for o in preferred]
            candidate_boxes = [bx for bx in candidate_boxes if bx is not None]
            near_box = _nearest_obj(dev, candidate_boxes, use_xy=True, max_distance=near_limit)
            if near_box is None:
                near_box = _nearest_obj(dev, candidate_boxes, use_xy=True)
            if near_box is not None:
                push(dev, near_box, "drop_box")

    # 3) Backbone entre cajas.
    ordered_boxes = []
    seen_box = set()
    for dev in devices:
        bx = box_by_source.get(_source_key(dev))
        if bx is None:
            continue
        bname = _safe_text(getattr(bx, "Name", ""))
        if bname and bname not in seen_box:
            seen_box.add(bname)
            ordered_boxes.append(bx)
    for bx in boxes:
        bname = _safe_text(getattr(bx, "Name", ""))
        if bname and bname not in seen_box:
            seen_box.add(bname)
            ordered_boxes.append(bx)

    if len(ordered_boxes) >= 3:
        ordered_boxes = _order_boxes_by_perimeter(ordered_boxes, board_obj=board_obj)

    if len(ordered_boxes) >= 2:
        for a, b in zip(ordered_boxes[:-1], ordered_boxes[1:]):
            push(a, b, "backbone")
    elif len(ordered_boxes) == 0 and len(devices) >= 2:
        for a, b in zip(devices[:-1], devices[1:]):
            if same_level_only and (not _same_level(a, b, level_tol)):
                _debug(
                    f"Backbone dispositivo-dispositivo omitido por distinta cota: "
                    f"{_safe_text(getattr(a, 'Label', a.Name))} -> {_safe_text(getattr(b, 'Label', b.Name))}"
                )
                continue
            push(a, b, "backbone")

    # 4) Conexion al tablero/ancla.
    if cfg.get("connect_to_board", True) and board_obj is not None:
        # Limitar el alimentador a los extremos del backbone empeora la
        # optimizacion espacial cuando existe una caja intermedia mejor ubicada.
        if ordered_boxes:
            nodes = list(ordered_boxes)
        else:
            nodes = list(devices)
        if nodes:
            near = _nearest_obj(board_obj, nodes, use_xy=True)
            if near is not None:
                push(near, board_obj, "feeder")

    return plan


def main():
    doc = App.ActiveDocument
    if doc is None:
        _err("No hay documento activo.")
        return

    if not GUI_UP:
        _err("Esta macro requiere FreeCADGui activo.")
        return

    selection_ctx = _selection_context(doc)
    selected_groups = list(selection_ctx.get("groups") or [])

    cfg = _ConfigDialog(doc, selection_ctx).run()
    if cfg is None:
        _warn("Operacion cancelada por el usuario.")
        return
    _set_debug_enabled(bool(cfg.get("debug_enabled", True)))
    _start_debug_session(cfg, selection_ctx)
    _log(f"Log de ejecucion: {_debug_log_path()}")

    anchor_obj = _find_object_by_name(doc, cfg.get("anchor_name", ""))
    if cfg.get("connect_to_board", True) and anchor_obj is None:
        _warn("Seleccione un tablero/ancla en el formulario o desactive la conexion al tablero.")
        return
    guide_objs = [o for o in _objects_by_names(doc, cfg.get("guide_names", [])) if _is_guide_route_candidate(o)]

    get_component_type = _import_component_classifier()
    if get_component_type is None:
        _warn("No se pudo importar component_classifier.py; se usara deteccion basica.")

    circuit_groups = _candidate_circuit_groups(doc, selected_groups)
    if not circuit_groups:
        _warn("No se encontraron grupos de circuito para procesar.")
        return
    circuit_groups = _sort_circuit_groups_manual(circuit_groups, cfg)

    stats = {
        "circuits": 0,
        "devices": 0,
        "boxes": 0,
        "planned": 0,
        "created": 0,
        "existing": 0,
        "skipped": 0,
        "errors": 0,
    }
    refresh_existing_routes = bool(cfg.get("refresh_existing_routes", False))

    jobs = []
    for cgroup in circuit_groups:
        circuit_id = _circuit_id_for_group(cgroup)
        devices, boxes = _collect_circuit_objects(
            cgroup,
            get_component_type=get_component_type,
            include_apagadores=bool(cfg.get("include_apagadores", True)),
        )
        if not devices and not boxes:
            continue

        box_by_source = _map_boxes_by_source(boxes)
        plan = _build_plan_for_circuit(
            circuit_group=cgroup,
            devices=devices,
            boxes=boxes,
            box_by_source=box_by_source,
            board_obj=anchor_obj,
            cfg=cfg,
        )
        if not plan:
            continue

        jobs.append({
            "job_key": _group_id(cgroup) or circuit_id,
            "group": cgroup,
            "circuit_id": circuit_id,
            "devices": devices,
            "boxes": boxes,
            "plan": plan,
        })

    if not jobs:
        _warn("No se encontraron circuitos con plan de conexion.")
        return

    feeder_lane_map, feeder_lane_count, feeder_lane_meta = _feeder_lane_map(jobs, anchor_obj, guide_objs, cfg)
    if feeder_lane_count <= 0:
        feeder_lane_count = 1
    if isinstance(feeder_lane_meta, dict) and feeder_lane_meta:
        jobs = sorted(
            jobs,
            key=lambda job: (
                int(feeder_lane_meta.get(job.get("job_key"), {}).get("plan_order", 10 ** 9)),
                _natural_key(job.get("circuit_id", "")),
            ),
        )

    try:
        doc.openTransaction("ElectricCR: conectar cajas a tablero auto")
        for job in jobs:
            cgroup = job["group"]
            circuit_id = job["circuit_id"]
            devices = list(job["devices"])
            boxes = list(job["boxes"])
            plan = list(job["plan"])

            stats["circuits"] += 1
            stats["devices"] += len(devices)
            stats["boxes"] += len(boxes)
            stats["planned"] += len(plan)

            conduit_txt = _safe_text(cfg.get("conduit_type", DEFAULT_CONDUIT)).upper()
            group_tuberias = _ensure_child_group(
                doc,
                cgroup,
                f"Tuberias_{conduit_txt}",
                prefix="Tuberias",
            )
            legacy_conex = _find_child_group_by_label(cgroup, "Conexiones")
            if refresh_existing_routes:
                board_name = _safe_text(getattr(anchor_obj, "Name", ""))
                removed_now = _delete_autoroute_feeders(doc, group_tuberias, board_name)
                removed_legacy = _delete_autoroute_feeders(doc, legacy_conex, board_name)
                removed_total = int(removed_now) + int(removed_legacy)
                if removed_total:
                    _log(f"Circuito '{circuit_id}': eliminados {removed_total} alimentadores existentes antes de recalcular.")
            existing_keys = set()
            if cfg.get("skip_existing", True):
                existing_keys.update(_collect_existing_route_keys(group_tuberias))
                # Compatibilidad con versiones anteriores que guardaban en Conexiones.
                moved_legacy = _migrate_autoroute_to_group(legacy_conex, group_tuberias)
                if moved_legacy:
                    _log(f"Circuito '{circuit_id}': migradas {moved_legacy} tuberias desde Conexiones a {group_tuberias.Label}.")
                existing_keys.update(_collect_existing_route_keys(legacy_conex))
            used_ports = defaultdict(set)
            route_rect_backbone = _route_rect_for_circuit([], boxes, cfg, board_obj=None, use_box_ports=False)
            route_rect_feeder = _route_rect_for_circuit(devices, boxes, cfg, board_obj=anchor_obj, use_box_ports=True)
            _debug(
                f"Circuito {_safe_text(circuit_id)} | rect_backbone={route_rect_backbone} "
                f"rect_feeder={route_rect_feeder}"
            )
            if bool(cfg.get("reserve_ports", True)):
                _reserve_existing_ports(group_tuberias, used_ports)
                legacy_conex = _find_child_group_by_label(cgroup, "Conexiones")
                _reserve_existing_ports(legacy_conex, used_ports)
            lane_index = int(feeder_lane_map.get(job["job_key"], 0))
            lane_meta = feeder_lane_meta.get(job["job_key"], {}) if isinstance(feeder_lane_meta, dict) else {}
            feeder_board_lane_index = int(lane_meta.get("face_index", lane_index))
            feeder_board_lane_count = int(lane_meta.get("face_count", feeder_lane_count))
            feeder_route_lane_index = int(lane_meta.get("route_index", feeder_board_lane_index))
            feeder_route_lane_count = int(lane_meta.get("route_count", feeder_board_lane_count))
            feeder_section_key = _safe_text(lane_meta.get("section_key", "")).strip()
            feeder_board_section_index = int(lane_meta.get("section_index", 0))
            feeder_board_section_count = int(lane_meta.get("section_count", 1))
            feeder_board_section_lane_index = int(lane_meta.get("section_lane_index", 0))
            feeder_board_section_lane_count = int(lane_meta.get("section_lane_count", feeder_board_lane_count))
            feeder_face = _safe_text(lane_meta.get("face", "")).strip()
            route_lane_index_for_offset = feeder_route_lane_index
            if feeder_face in ("Top", "Bottom"):
                route_lane_index_for_offset = max(0, feeder_route_lane_count - 1 - feeder_route_lane_index)
            feeder_lane_vec = _lane_offset_vector(
                lane_index=route_lane_index_for_offset,
                lane_count=feeder_route_lane_count,
                separation=float(cfg.get("circuit_separation", DEFAULT_CIRCUIT_SEPARATION)),
                axis=_safe_text(cfg.get("feeder_axis", DEFAULT_FEEDER_AXIS)),
            )

            for src_obj, dst_obj, link_kind in plan:
                try:
                    use_perimeter = bool(cfg.get("route_by_perimeter", True)) and (link_kind in ("feeder", "backbone"))
                    active_rect = None
                    if use_perimeter:
                        active_rect = route_rect_backbone if link_kind == "backbone" else route_rect_feeder
                    status, _route_key = _connect_pair(
                        doc=doc,
                        src_obj=src_obj,
                        dst_obj=dst_obj,
                        circuit_id=circuit_id,
                        conduit_type=conduit_txt,
                        diameter=float(cfg.get("diameter", DEFAULT_DIAMETER)),
                        bend_radius=float(cfg.get("bend_radius", DEFAULT_BEND_RADIUS)),
                        route_z=float(cfg.get("route_z", DEFAULT_ROUTE_Z)),
                        orthogonal_route=bool(cfg.get("orthogonal_route", True)),
                        route_by_perimeter=use_perimeter,
                        route_rect=active_rect,
                        guide_objs=guide_objs,
                        guide_section_key=feeder_section_key,
                        link_kind=link_kind,
                        board_obj=anchor_obj,
                        anchor_face=_safe_text(cfg.get("anchor_face", "Auto")),
                        anchor_faces=_anchor_allowed_faces(cfg),
                        feeder_lane_vec=feeder_lane_vec,
                        feeder_board_lane_index=feeder_board_lane_index,
                        feeder_board_lane_count=feeder_board_lane_count,
                        feeder_board_lane_separation=float(cfg.get("circuit_separation", DEFAULT_CIRCUIT_SEPARATION)),
                        feeder_board_section_index=feeder_board_section_index,
                        feeder_board_section_count=feeder_board_section_count,
                        feeder_board_section_lane_index=feeder_board_section_lane_index,
                        feeder_board_section_lane_count=feeder_board_section_lane_count,
                        reserve_ports=bool(cfg.get("reserve_ports", True)),
                        used_ports=used_ports,
                        group_target=group_tuberias,
                        existing_keys=existing_keys,
                        skip_existing=bool(cfg.get("skip_existing", True)),
                    )
                    if status == "created":
                        stats["created"] += 1
                    elif status == "existing":
                        stats["existing"] += 1
                    else:
                        stats["skipped"] += 1
                except Exception as ex:
                    stats["errors"] += 1
                    _debug(
                        f"Excepcion conectando {_safe_text(getattr(src_obj, 'Name', ''))} -> "
                        f"{_safe_text(getattr(dst_obj, 'Name', ''))}: {ex}"
                    )
                    _warn(
                        f"Fallo conectando '{_safe_text(getattr(src_obj, 'Label', src_obj.Name))}'"
                        f" -> '{_safe_text(getattr(dst_obj, 'Label', dst_obj.Name))}': {ex}"
                    )

        doc.recompute()
        doc.commitTransaction()
    except Exception as ex:
        try:
            doc.abortTransaction()
        except Exception:
            pass
        _err(f"Fallo general: {ex}")
        return

    _log(
        "Finalizado. "
        f"Circuitos={stats['circuits']}, "
        f"Dispositivos={stats['devices']}, Cajas={stats['boxes']}, "
        f"Plan={stats['planned']}, Creadas={stats['created']}, "
        f"Existentes={stats['existing']}, Omitidas={stats['skipped']}, Errores={stats['errors']}. "
        f"Conduit={_safe_text(cfg.get('conduit_type', DEFAULT_CONDUIT)).upper()} "
        f"Diametro={float(cfg.get('diameter', DEFAULT_DIAMETER)):.1f} mm "
        f"RadioCurvatura={float(cfg.get('bend_radius', DEFAULT_BEND_RADIUS)):.1f} mm "
        f"RutaZ={float(cfg.get('route_z', DEFAULT_ROUTE_Z)):.1f} mm. "
        f"PerimetroMuros={'SI' if cfg.get('route_by_perimeter', True) else 'NO'} "
        f"OffsetPerimetro={float(cfg.get('wall_margin', DEFAULT_WALL_OFFSET)):.1f} mm "
        f"SepCircuitos={float(cfg.get('circuit_separation', DEFAULT_CIRCUIT_SEPARATION)):.1f} mm "
        f"EjeAlimentador={_safe_text(cfg.get('feeder_axis', DEFAULT_FEEDER_AXIS))} "
        f"CaraTablero={_safe_text(cfg.get('anchor_face', 'Auto')) or 'Auto'} "
        f"CarasPermitidas={','.join(_anchor_allowed_faces(cfg))} "
        f"OrdenManualCircuitos={'SI' if cfg.get('manual_circuit_order_enabled', False) else 'NO'} "
        f"OrdenManualSecciones={'SI' if cfg.get('manual_guide_order_enabled', False) else 'NO'} "
        f"OrdenManualPorSeccion={'SI' if cfg.get('manual_section_circuit_order_enabled', False) else 'NO'} "
        f"DirectaMismaCota={'SI' if cfg.get('direct_same_level_only', True) else 'NO'} "
        f"TolCota={float(cfg.get('device_level_tolerance', DEFAULT_DEVICE_LEVEL_TOLERANCE)):.1f} mm "
        f"RutasGuia={len(guide_objs)}. "
        f"ActualizarRutas={'SI' if refresh_existing_routes else 'NO'}. "
        "Grupo destino por circuito: <Circuito>/Tuberias_<EMT|PVC>."
    )
    _debug("Fin de ejecucion.")


if __name__ == "__main__":
    main()

import FreeCAD
import FreeCADGui
import Part
import Draft
import os
import sys
_THIS_DIR = os.path.dirname(__file__) if '__file__' in globals() else ''
if _THIS_DIR and _THIS_DIR not in sys.path:
    sys.path.insert(0, _THIS_DIR)
import importlib
import conexiones_grouping as _conexiones_grouping_mod
_conexiones_grouping_mod = importlib.reload(_conexiones_grouping_mod)
ensure_conexiones_group = _conexiones_grouping_mod.ensure_conexiones_group
def _make_wire(points):
    maker = getattr(Draft, "make_wire", None)
    if maker is None:
        maker = getattr(Draft, "makeWire", None)
    if maker is None:
        raise RuntimeError("No se encontro Draft.make_wire ni Draft.makeWire")

    attempts = [
        lambda: maker(points, closed=False, face=False),
        lambda: maker(points, False, False),
        lambda: maker(points, False),
        lambda: maker(points),
    ]
    last_err = None
    for attempt in attempts:
        try:
            return attempt()
        except Exception as ex:
            last_err = ex
    raise RuntimeError(f"No se pudo crear wire: {last_err}")


def conectar_objetos_por_bordes():
    doc = FreeCAD.ActiveDocument
    if doc is None:
        FreeCAD.Console.PrintError("No hay documento activo.\n")
        return

    selected_objects = FreeCADGui.Selection.getSelectionEx()

    if len(selected_objects) < 2:
        FreeCAD.Console.PrintError("Debe seleccionar al menos dos objetos y puntos correspondientes (vertices o bordes).\n")
        return

    grupo_padre = None
    for obj in doc.Objects:
        if obj.TypeId == "App::DocumentObjectGroup" and all(sel_obj.Object in obj.Group for sel_obj in selected_objects):
            grupo_padre = obj
            break

    if grupo_padre:
        FreeCAD.Console.PrintMessage(f"Grupo padre encontrado: {grupo_padre.Name}\n")
    else:
        FreeCAD.Console.PrintWarning("Sin grupo comun; se usara Conexiones_Huerfanas.\n")

    conexiones_grupo = ensure_conexiones_group(
        doc,
        parent_group=grupo_padre,
        objects=[sel.Object for sel in selected_objects if getattr(sel, "Object", None)],
    )

    conexiones_realizadas = set()

    def obtener_punto_y_direccion_borde(selection_detail):
        if selection_detail.HasSubObjects:
            for sub_obj in selection_detail.SubObjects:
                if isinstance(sub_obj, Part.Edge):
                    punto_medio = sub_obj.CenterOfMass
                    tangente = sub_obj.tangentAt(0.5)
                    direccion_perpendicular = FreeCAD.Vector(-tangente.y, tangente.x, 0)
                    return punto_medio, direccion_perpendicular
        return selection_detail.Object.Shape.BoundBox.Center, None

    puntos_seleccionados = []
    for selection_detail in selected_objects:
        punto, direccion = obtener_punto_y_direccion_borde(selection_detail)
        puntos_seleccionados.append((selection_detail.Object, punto, direccion))

    if len(puntos_seleccionados) < 2:
        FreeCAD.Console.PrintError("No hay suficientes puntos seleccionados para conectar.\n")
        return

    for i in range(len(puntos_seleccionados) - 1):
        objeto1, punto1, direccion1 = puntos_seleccionados[i]
        objeto2, punto2, direccion2 = puntos_seleccionados[i + 1]

        if (objeto1.Label, objeto2.Label) in conexiones_realizadas or (objeto2.Label, objeto1.Label) in conexiones_realizadas:
            continue

        puntos_conexion = [punto1]

        if direccion1 and direccion2:
            punto_intermedio1 = punto1 + direccion1 * 20
            puntos_conexion.append(punto_intermedio1)

            if abs(punto1.x - punto2.x) > 1e-3:
                punto_intermedio2 = FreeCAD.Vector(punto2.x, punto_intermedio1.y, punto1.z)
                puntos_conexion.append(punto_intermedio2)
            if abs(punto1.y - punto2.y) > 1e-3:
                punto_intermedio3 = FreeCAD.Vector(punto2.x, punto2.y, punto1.z)
                puntos_conexion.append(punto_intermedio3)

        puntos_conexion.append(punto2)

        wire_obj = _make_wire(puntos_conexion)
        wire_obj.Label = f"Conexion_{objeto1.Label}_{objeto2.Label}"
        conexiones_grupo.addObject(wire_obj)

        conexiones_realizadas.add((objeto1.Label, objeto2.Label))

    doc.recompute()


# Ejecutar la funcion
conectar_objetos_por_bordes()

# -*- coding: utf-8 -*-
# MenuText: Conectar tableros y equipos por cara superior (Legacy)
# ToolTip: Wrapper compatible del motor general de alimentadores
# Icon: Conectar_Tableros_Cara_Superior.svg
# Toolbar: Conectar Legacy
# Transaction: self

"""Wrapper tablero/equipo -> tablero aguas arriba.

La cara, distribucion, ruteo y metadatos pertenecen al motor Python general.
Compatible con FreeCAD 1.1.3. Revision: 2026-08-08.
"""

from pathlib import Path
import sys
import FreeCAD as App

try:
    import FreeCADGui as Gui
except Exception:
    Gui = None


def _services():
    root = Path(__file__).resolve().parent.parent
    if str(root) not in sys.path:
        sys.path.insert(0, str(root))
    from ElectricCR.electriccr.connections import assignments, feeders, panels

    return assignments, feeders, panels


def run(source=None, destination=None, circuit_id="", source_slot_index=None, source_slot_count=None):
    assignments, feeders, panels = _services()
    doc = App.ActiveDocument
    if doc is None:
        return None
    selected = []
    if Gui is not None:
        try:
            selected = [obj for obj in (Gui.Selection.getSelection() or []) if panels.is_panel(obj) or assignments.is_connectable_equipment(obj)]
        except Exception:
            selected = []
    source = source or (selected[0] if len(selected) >= 1 else None)
    destination = destination or (selected[1] if len(selected) >= 2 else None)
    if source is None or destination is None or source is destination or not panels.is_panel(source):
        App.Console.PrintWarning("[ElectricCR][FEEDER] Seleccione primero el tablero aguas arriba y luego el equipo destino.\n")
        return None
    cid = panels.text(circuit_id).strip() or assignments.circuit_id(destination)
    if not cid:
        App.Console.PrintWarning("[ElectricCR][FEEDER] El equipo destino no tiene circuito asignado.\n")
        return None
    record = {"object": destination, "panel": source, "circuit_id": cid, "source": "Seleccion"}
    result = feeders.connect_equipment_feeders(doc, [record])
    route = result["routes"][0] if result and result.get("routes") else None
    if route is None:
        return None
    for ptype, name, group, description in (
        ("App::PropertyInteger", "RanuraTableroOrigen", "Puertos", "Ranura asignada, uno basada"),
        ("App::PropertyInteger", "CantidadRanurasTableroOrigen", "Puertos", "Cantidad de llegadas distribuidas"),
        ("App::PropertyInteger", "FaceIndexTableroOrigen", "Puertos", "Indice de cara superior"),
        ("App::PropertyString", "CaraTableroOrigen", "Puertos", "Cara superior usada"),
    ):
        if name not in set(getattr(route, "PropertiesList", []) or []):
            route.addProperty(ptype, name, group, description)
    route.RanuraTableroOrigen = int(source_slot_index) + 1 if source_slot_index is not None else int(route.SlotTablero)
    route.CantidadRanurasTableroOrigen = int(source_slot_count) if source_slot_count is not None else int(route.CantidadSlotsTablero)
    route.FaceIndexTableroOrigen = int(route.FaceIndexTablero)
    route.CaraTableroOrigen = str(route.CaraTablero)
    route.Tipo = "AlimentadorEntreTableros"
    return route


if __name__ == "__main__":
    run()

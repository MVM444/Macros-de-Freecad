# -*- coding: utf-8 -*-
# MenuText: Conectar Circuitos TP a Cara Superior del Tablero (Legacy)
# Icon: Conectar/Conectar_Circuitos_TP_a_Cara_Superior_Tablero.svg
# Toolbar: Conectar Legacy
# Transaction: self

"""Wrapper compatible TP del motor general ElectricCR.

No contiene geometria propia ni es biblioteca de otras macros. El respaldo de
la version especializada esta en Backups/consolidacion_conexiones_20260808.
Compatible con FreeCAD 1.1.3. Revision: 2026-08-08.
"""

from pathlib import Path
import sys
import FreeCAD as App


def main(doc_override=None, cfg_override=None):
    root = Path(__file__).resolve().parent.parent
    if str(root) not in sys.path:
        sys.path.insert(0, str(root))
    from ElectricCR.electriccr.connections import feeders

    doc = doc_override or App.ActiveDocument
    if doc is None:
        return None
    result = feeders.connect_circuit_feeders(doc, panel_code="TP", circuit_prefix="TP", cfg=cfg_override)
    return {
        "tablero": "TP",
        "circuitos": len(result.get("routes", [])),
        "creados": result.get("created", 0),
        "actualizados": result.get("updated", 0),
        "errores": result.get("errors", []),
    } if result is not None else None


if __name__ == "__main__":
    main()

import FreeCAD
import FreeCADGui
import Draft
import os
import sys
_THIS_DIR = os.path.dirname(__file__) if '__file__' in globals() else ''
if _THIS_DIR and _THIS_DIR not in sys.path:
    sys.path.insert(0, _THIS_DIR)
import importlib
import conexiones_grouping as _conexiones_grouping_mod
_conexiones_grouping_mod = importlib.reload(_conexiones_grouping_mod)
ensure_conexiones_group = _conexiones_grouping_mod.ensure_conexiones_group
def conectar_objetos_arbol():
    doc = FreeCAD.ActiveDocument
    if doc is None:
        FreeCAD.Console.PrintError("No hay documento activo.\n")
        return

    # Obtener el objeto seleccionado
    selected_objects = FreeCADGui.Selection.getSelection()
    if not selected_objects:
        FreeCAD.Console.PrintError("No se ha seleccionado ningun objeto.\n")
        return

    # Verificar si el objeto seleccionado es un grupo
    if selected_objects[0].TypeId == "App::DocumentObjectGroup":
        grupo = selected_objects[0]
    else:
        grupo = None
        for obj in doc.Objects:
            if obj.TypeId == "App::DocumentObjectGroup" and selected_objects[0] in obj.Group:
                grupo = obj
                break
        if grupo is None:
            FreeCAD.Console.PrintError("El objeto seleccionado no pertenece a ningun grupo.\n")
            return

    FreeCAD.Console.PrintMessage(f"Grupo seleccionado: {grupo.Name}\n")

    # Filtrar solo objetos conectables con Placement y numeracion en Label
    objetos_numerados = sorted(
        [
            obj
            for obj in grupo.Group
            if hasattr(obj, "Placement")
            and not hasattr(obj, "Group")
            and any(char.isdigit() for char in obj.Label)
        ],
        key=lambda x: int("".join(filter(str.isdigit, x.Label)))
        if any(char.isdigit() for char in x.Label)
        else float("inf"),
    )

    if len(objetos_numerados) < 2:
        FreeCAD.Console.PrintError("No hay suficientes objetos numerados para conectar.\n")
        return

    conexiones_grupo = ensure_conexiones_group(doc, parent_group=grupo, objects=objetos_numerados)

    conexiones_realizadas = set()

    for i in range(len(objetos_numerados) - 1):
        objeto1 = objetos_numerados[i]
        objeto2 = objetos_numerados[i + 1]

        if (objeto1.Label, objeto2.Label) in conexiones_realizadas or (objeto2.Label, objeto1.Label) in conexiones_realizadas:
            continue

        puntos = [objeto1.Placement.Base]

        # Agregar puntos intermedios para mantener angulos rectos
        if objeto1.Placement.Base.x != objeto2.Placement.Base.x:
            puntos.append(FreeCAD.Vector(objeto2.Placement.Base.x, objeto1.Placement.Base.y, objeto1.Placement.Base.z))
        if objeto1.Placement.Base.y != objeto2.Placement.Base.y:
            puntos.append(FreeCAD.Vector(objeto2.Placement.Base.x, objeto2.Placement.Base.y, objeto1.Placement.Base.z))

        puntos.append(objeto2.Placement.Base)

        wire = Draft.make_wire(puntos, closed=False, face=False)
        wire.Label = f"Conexion_{objeto1.Label}_{objeto2.Label}"
        conexiones_grupo.addObject(wire)

        conexiones_realizadas.add((objeto1.Label, objeto2.Label))

    doc.recompute()


# Ejecutar la funcion para conectar objetos en el grupo seleccionado
conectar_objetos_arbol()

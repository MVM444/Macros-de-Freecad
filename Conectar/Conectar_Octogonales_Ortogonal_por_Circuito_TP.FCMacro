# -*- coding: utf-8 -*-
# MenuText: Conectar Octogonales por Circuito TP (Legacy)
# Icon: Conectar/Conectar_Octogonales_Ortogonal_por_Circuito_TP.svg
# Toolbar: Conectar Legacy
# Transaction: self

"""Wrapper TP del backbone general ElectricCR. Revision: 2026-08-08."""

from pathlib import Path
import sys
import FreeCAD as App


def main(doc_override=None, cfg_override=None):
    root = Path(__file__).resolve().parent.parent
    if str(root) not in sys.path:
        sys.path.insert(0, str(root))
    from ElectricCR.electriccr.connections import backbone

    doc = doc_override or App.ActiveDocument
    if doc is None:
        return None
    result = backbone.connect_backbone(doc, cfg=cfg_override, circuit_prefix="TP")
    return {
        "circuitos": len({getattr(route, "CircuitoID", "") for route in result.get("routes", [])}),
        "ramales": len(result.get("routes", [])),
        "creados": result.get("created", 0),
        "actualizados": result.get("updated", 0),
        "eliminados_obsoletos": result.get("deleted", 0),
        "errores": result.get("errors", []),
    } if result is not None else None


if __name__ == "__main__":
    main()

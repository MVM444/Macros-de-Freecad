import FreeCAD
import FreeCADGui
import Draft
import os
import sys
_THIS_DIR = os.path.dirname(__file__) if '__file__' in globals() else ''
if _THIS_DIR and _THIS_DIR not in sys.path:
    sys.path.insert(0, _THIS_DIR)
import importlib
import conexiones_grouping as _conexiones_grouping_mod
_conexiones_grouping_mod = importlib.reload(_conexiones_grouping_mod)
ensure_conexiones_group = _conexiones_grouping_mod.ensure_conexiones_group
def _make_wire(points):
    maker = getattr(Draft, "make_wire", None)
    if maker is None:
        maker = getattr(Draft, "makeWire", None)
    if maker is None:
        raise RuntimeError("No se encontro Draft.make_wire ni Draft.makeWire")

    attempts = [
        lambda: maker(points, closed=False, face=False),
        lambda: maker(points, False, False),
        lambda: maker(points, False),
        lambda: maker(points),
    ]
    last_err = None
    for attempt in attempts:
        try:
            return attempt()
        except Exception as ex:
            last_err = ex
    raise RuntimeError(f"No se pudo crear wire: {last_err}")


def conectar_objetos_arbol():
    doc = FreeCAD.ActiveDocument
    if doc is None:
        FreeCAD.Console.PrintError("No hay documento activo.\n")
        return

    selected_objects = FreeCADGui.Selection.getSelection()
    if not selected_objects:
        FreeCAD.Console.PrintError("No se ha seleccionado ningun objeto.\n")
        return

    if selected_objects[0].TypeId == "App::DocumentObjectGroup":
        grupo = selected_objects[0]
    else:
        grupo = None
        for obj in doc.Objects:
            if obj.TypeId == "App::DocumentObjectGroup" and selected_objects[0] in obj.Group:
                grupo = obj
                break
        if grupo is None:
            FreeCAD.Console.PrintError("El objeto seleccionado no pertenece a ningun grupo.\n")
            return

    FreeCAD.Console.PrintMessage(f"Grupo seleccionado: {grupo.Name}\n")

    objetos_numerados = sorted(
        [
            obj
            for obj in grupo.Group
            if hasattr(obj, "Placement")
            and not hasattr(obj, "Group")
            and any(char.isdigit() for char in obj.Label)
        ],
        key=lambda x: int("".join(filter(str.isdigit, x.Label)))
        if any(char.isdigit() for char in x.Label)
        else float("inf"),
    )

    if len(objetos_numerados) < 2:
        FreeCAD.Console.PrintError("No hay suficientes objetos numerados para conectar.\n")
        return

    conexiones_grupo = ensure_conexiones_group(doc, parent_group=grupo, objects=objetos_numerados)

    conexiones_realizadas = set()

    for i in range(len(objetos_numerados) - 1):
        objeto1 = objetos_numerados[i]
        objeto2 = objetos_numerados[i + 1]

        if (objeto1.Label, objeto2.Label) in conexiones_realizadas or (objeto2.Label, objeto1.Label) in conexiones_realizadas:
            continue

        puntos = [objeto1.Placement.Base]

        if objeto1.Placement.Base.x != objeto2.Placement.Base.x:
            puntos.append(FreeCAD.Vector(objeto2.Placement.Base.x, objeto1.Placement.Base.y, objeto1.Placement.Base.z))
        if objeto1.Placement.Base.y != objeto2.Placement.Base.y:
            puntos.append(FreeCAD.Vector(objeto2.Placement.Base.x, objeto2.Placement.Base.y, objeto1.Placement.Base.z))

        puntos.append(objeto2.Placement.Base)

        wire_obj = _make_wire(puntos)
        wire_obj.Label = f"Conexion_{objeto1.Label}_{objeto2.Label}"
        conexiones_grupo.addObject(wire_obj)
        if hasattr(wire_obj, "ViewObject"):
            wire_obj.ViewObject.Visibility = True

        conexiones_realizadas.add((objeto1.Label, objeto2.Label))

    doc.recompute()


# Ejecutar la funcion para conectar objetos en el grupo seleccionado
conectar_objetos_arbol()

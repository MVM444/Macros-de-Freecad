import FreeCAD
import FreeCADGui
import unicodedata

def normalize_text(text):
    """ Normaliza un texto eliminando caracteres especiales. """
    try:
        return unicodedata.normalize("NFKD", text).encode("ascii", "ignore").decode("ascii")
    except Exception:
        return "ERROR_CODIFICACION"

def safe_str(value):
    """ Convierte valores a cadena y maneja errores de codificacion. """
    try:
        return str(value)
    except Exception:
        return "ERROR_VALOR"

def _col_index(letter):
    try:
        return ord(letter.upper()) - 64
    except Exception:
        return 0

def _ensure_min_cols(sheet, min_cols):
    try:
        if hasattr(sheet, "ColumnCount") and sheet.ColumnCount < min_cols:
            sheet.ColumnCount = min_cols
    except Exception:
        pass

def _ensure_min_rows(sheet, min_rows):
    try:
        if hasattr(sheet, "RowCount") and sheet.RowCount < min_rows:
            sheet.RowCount = min_rows
    except Exception:
        pass

def _safe_get(sheet, addr, default=""):
    try:
        col = _col_index(addr[:1])
        row = int(addr[1:])
        if hasattr(sheet, "ColumnCount") and sheet.ColumnCount < col:
            return default
        if hasattr(sheet, "RowCount") and sheet.RowCount < row:
            return default
        return sheet.get(addr)
    except Exception:
        return default

def _safe_set(sheet, addr, value):
    try:
        col = _col_index(addr[:1])
        row = int(addr[1:])
        _ensure_min_cols(sheet, col)
        _ensure_min_rows(sheet, row)
        sheet.set(addr, value)
        return True
    except Exception:
        return False

def _as_mm(value):
    try:
        return float(getattr(value, "Value", value))
    except Exception:
        return 0.0

def _norm_key(value):
    s = str(value or "").strip().lower()
    s = unicodedata.normalize("NFKD", s)
    s = "".join(ch for ch in s if not unicodedata.combining(ch))
    out = []
    for ch in s:
        if ch.isalnum():
            out.append(ch)
    return "".join(out)

def _find_group_by_key(doc, wanted_key):
    for obj in getattr(doc, "Objects", []) or []:
        if getattr(obj, "TypeId", "") != "App::DocumentObjectGroup":
            continue
        if _norm_key(getattr(obj, "Label", "")) == wanted_key:
            return obj
        if _norm_key(getattr(obj, "Name", "")) == wanted_key:
            return obj
    return None

def _create_group(doc, label):
    base = "".join(ch if ch.isalnum() else "_" for ch in str(label or "").strip()) or "Grupo"
    name = base
    idx = 2
    while doc.getObject(name) is not None:
        name = "{}_{}".format(base, idx)
        idx += 1
    grp = doc.addObject("App::DocumentObjectGroup", name)
    try:
        grp.Label = label
    except Exception:
        pass
    return grp

def _ensure_calculation_group(doc):
    for candidate in ("Hojas de Calculo", "Hojas de Cálculo", "Hojas_Calculo"):
        grp = _find_group_by_key(doc, _norm_key(candidate))
        if grp is not None:
            try:
                grp.Label = "Hojas de Calculo"
            except Exception:
                pass
            return grp
    legacy = _find_group_by_key(doc, _norm_key("Calculos"))
    if legacy is not None:
        try:
            legacy.Label = "Hojas de Calculo"
        except Exception:
            pass
        return legacy
    return _create_group(doc, "Hojas de Calculo")

def _add_to_group(group, obj):
    if group is None or obj is None:
        return
    try:
        if obj not in (getattr(group, "Group", []) or []):
            group.addObject(obj)
    except Exception:
        pass

def calcular_area_y_exportar_a_spreadsheet():
    doc = FreeCAD.ActiveDocument
    selected_objects = FreeCADGui.Selection.getSelection()

    if not selected_objects:
        FreeCAD.Console.PrintError("No se ha seleccionado ningun objeto.\n")
        return

    # Si se selecciona un objeto dentro de un grupo, seleccionar el grupo completo
    if selected_objects[0].TypeId != 'App::DocumentObjectGroup':
        for obj in doc.Objects:
            if obj.TypeId == 'App::DocumentObjectGroup' and selected_objects[0] in obj.Group:
                selected_objects = [obj]
                FreeCAD.Console.PrintMessage("Seleccion detectada dentro de un grupo. Se selecciona el grupo completo.\n")
                break

    grupo = selected_objects[0]
    if grupo.TypeId != 'App::DocumentObjectGroup':
        FreeCAD.Console.PrintError("El objeto seleccionado no es un grupo.\n")
        return

    # Crear la hoja de calculo si no existe
    hoja = None
    for obj in doc.Objects:
        if obj.TypeId == 'Spreadsheet::Sheet' and obj.Name == 'DatosRecintos':
            hoja = obj
            break
    
    if not hoja:
        hoja = doc.addObject('Spreadsheet::Sheet', 'DatosRecintos')

    calc_group = _ensure_calculation_group(doc)
    _add_to_group(calc_group, hoja)
    
    hoja.Visibility = True  # Asegura que la hoja de calculo sea visible

    data_recintos = {}

    # Contador de objetos procesados
    objetos_procesados = 0

    for obj in grupo.Group:
        if hasattr(obj, 'Shape') and obj.Shape and (obj.Shape.Faces or obj.Shape.Edges):
            try:
                bounds = obj.Shape.BoundBox
                largo = bounds.XLength / 1000  # mm a m
                ancho = bounds.YLength / 1000  # mm a m
                altura = bounds.ZLength / 1000  # mm a m
                area_mm2 = obj.Shape.Area if obj.Shape.Faces else 0.0
                if not obj.Shape.Faces:
                    FreeCAD.Console.PrintWarning(
                        f"El objeto {obj.Label} no tiene una cara definida. Se recomienda activar 'Make Face' en sus propiedades.\n"
                    )
                    length = _as_mm(getattr(obj, "Length", 0.0))
                    height = _as_mm(getattr(obj, "Height", 0.0))
                    if length > 0.0 and height > 0.0:
                        area_mm2 = length * height
                    else:
                        area_mm2 = bounds.XLength * bounds.YLength
                area = area_mm2 / 1000000.0
                rows = getattr(obj, 'Rows', 0)
                columns = getattr(obj, 'Columns', 0)

                nombre_normalizado = normalize_text(obj.Label.rsplit('_', 1)[0])
                data_recintos[nombre_normalizado] = {
                    "Recinto": normalize_text(obj.Label),
                    "Area": round(area, 2),
                    "Largo": round(largo, 2),
                    "Ancho": round(ancho, 2),
                    "Altura": round(altura, 2),
                    "Rows": safe_str(rows),
                    "Columns": safe_str(columns)
                }
                objetos_procesados += 1
                FreeCAD.Console.PrintMessage(f"Anadido: {obj.Label}\n")
            except AttributeError:
                FreeCAD.Console.PrintError(f"Error al obtener propiedades: {obj.Label}\n")
        else:
            FreeCAD.Console.PrintMessage(f"Objeto sin caras ni aristas procesables: {obj.Label}\n")

    if objetos_procesados == 0:
        FreeCAD.Console.PrintWarning("No se encontraron objetos validos para exportar.\n")
        return

    # Encabezados de la hoja de calculo
    headers = ["Recinto", "Area (m^2)", "Largo (m)", "Ancho (m)", "Altura (m)", "Filas", "Columnas", "Descripcion"]
    _ensure_min_cols(hoja, len(headers))
    _ensure_min_rows(hoja, 2)
    for col, header in enumerate(headers, start=1):
        _safe_set(hoja, f"{chr(64 + col)}1", header)

    # Llenar la hoja de calculo sin borrar la columna Descripcion existente
    for fila, (key, value) in enumerate(data_recintos.items(), start=2):
        try:
            _safe_set(hoja, f"A{fila}", value["Recinto"])
            _safe_set(hoja, f"B{fila}", safe_str(value["Area"]))
            _safe_set(hoja, f"C{fila}", safe_str(value["Largo"]))
            _safe_set(hoja, f"D{fila}", safe_str(value["Ancho"]))
            _safe_set(hoja, f"E{fila}", safe_str(value["Altura"]))
            _safe_set(hoja, f"F{fila}", value["Rows"])
            _safe_set(hoja, f"G{fila}", value["Columns"])
            existing_value = _safe_get(hoja, f"H{fila}")
            if existing_value is None:
                existing_value = ""
            _safe_set(hoja, f"H{fila}", existing_value)
        except Exception as e:
            FreeCAD.Console.PrintError(f"Error al escribir datos en la fila {fila}: {e}\n")

    # Forzar recomputo de la hoja de calculo
    hoja.recompute()
    
    # Recomputa el documento para aplicar los cambios
    doc.recompute()
    FreeCAD.Console.PrintMessage(f"Datos exportados exitosamente a la hoja de calculo. ({objetos_procesados} objetos procesados)\n")

# Ejecutar la funcion
calcular_area_y_exportar_a_spreadsheet()

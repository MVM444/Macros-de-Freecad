# -*- coding: utf-8 -*-
# MenuText: Conectar Circuitos TCOM a Cara Superior del Tablero (Legacy)
# Icon: Conectar/Conectar_Circuitos_TCOM_a_Cara_Superior_Tablero.svg
# Toolbar: Conectar Legacy
# Transaction: self

"""Wrapper compatible TCOM del motor general ElectricCR.

No carga la macro TP ni contiene geometria propia. Compatible con FreeCAD
1.1.3. Revision: 2026-08-08.
"""

from pathlib import Path
import sys
import FreeCAD as App


def main(doc_override=None, cfg_override=None):
    root = Path(__file__).resolve().parent.parent
    if str(root) not in sys.path:
        sys.path.insert(0, str(root))
    from ElectricCR.electriccr.connections import feeders

    doc = doc_override or App.ActiveDocument
    if doc is None:
        return None
    result = feeders.connect_circuit_feeders(doc, panel_code="TCOM", circuit_prefix="TCOM", cfg=cfg_override)
    return {
        "tablero": "TCOM",
        "circuitos": len(result.get("routes", [])),
        "creados": result.get("created", 0),
        "actualizados": result.get("updated", 0),
        "errores": result.get("errors", []),
    } if result is not None else None


if __name__ == "__main__":
    main()

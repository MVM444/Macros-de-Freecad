# -*- coding: utf-8 -*-
# MenuText: Insertar Cajas Octogonales Encima...
# Icon: Cajas/Insertar_Cajas_Octogonales_Encima.svg

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

"""
Inserta cajas EMT octogonales encima de uno o varios objetos seleccionados.

Incluye:
- Altura objetivo de la caja (SNPT en mm).
- Conexion opcional desde objeto hacia caja:
  - EMT Solido
  - EMT Flexible
  - Sin conexion
- Asignacion automatica a grupos:
  <contenedor_funcional>/Cajas_Octogonales
  <contenedor_funcional>/Conexiones_3D
"""

from pathlib import Path
import importlib
import json
import re
import sys
import unicodedata

import FreeCAD as App
import Part

try:
    import FreeCADGui as Gui
    GUI_UP = True
except Exception:
    Gui = None
    GUI_UP = False

try:
    from PySide2 import QtWidgets, QtCore
except Exception:
    try:
        from PySide import QtGui as QtWidgets  # type: ignore
        from PySide import QtCore  # type: ignore
    except Exception:
        QtWidgets = None
        QtCore = None


DEFAULT_DIAMETER = 22.2
DEFAULT_SNPT = 3000.0
DEFAULT_CONN = "EMT_Solido"
NAME_PREFIX = "Caja EMT Octogonal"
PARAM_PATH = "User parameter:BaseApp/Preferences/Mod/ElectricCR/CajaEncima"

LEGACY_CONEX_LABELS = ("Conexiones_Luminarias_Cajas", "Conexiones_Luminarias_Cajas_3D")

SKIP_CONTAINER_HINTS = {
    "conexion",
    "conexiones",
    "ramales",
    "ramal",
    "alimentador",
    "alimentadores",
    "componente",
    "componentes",
    "circuitos",
    "recintos",
    "cajas_octogonales",
    "cajas",
    "conexiones_3d",
}
DEVICE_BUCKET_HINTS = {
    "apagador",
    "luminaria",
    "tomacorr",
    "toma",
    "sensor",
    "ventilador",
    "equipos",
    "salida",
}


def _log(msg):
    App.Console.PrintMessage(f"[CAJA_ENCIMA][INFO] {msg}\n")


def _warn(msg):
    App.Console.PrintWarning(f"[CAJA_ENCIMA][WARN] {msg}\n")


def _err(msg):
    App.Console.PrintError(f"[CAJA_ENCIMA][ERROR] {msg}\n")


def _prefs():
    try:
        return App.ParamGet(PARAM_PATH)
    except Exception:
        return None


def _pref_get_float(key, default):
    p = _prefs()
    if p is None:
        return float(default)
    try:
        return float(p.GetFloat(str(key), float(default)))
    except Exception:
        return float(default)


def _pref_get_str(key, default):
    p = _prefs()
    if p is None:
        return str(default)
    try:
        out = p.GetString(str(key), str(default))
        return str(out) if out is not None else str(default)
    except Exception:
        return str(default)


def _save_cfg(cfg):
    p = _prefs()
    if p is None:
        return
    try:
        p.SetFloat("altura_mm", float(cfg.get("altura_mm", DEFAULT_SNPT)))
        p.SetFloat("diametro_mm", float(cfg.get("diametro_mm", DEFAULT_DIAMETER)))
        p.SetString("tipo_conexion", str(cfg.get("tipo_conexion", DEFAULT_CONN)))
    except Exception:
        pass


def _safe_text(value):
    try:
        return str(value or "")
    except Exception:
        return ""


def _normalize(text):
    s = _safe_text(text).strip().lower()
    if not s:
        return ""
    s = unicodedata.normalize("NFKD", s)
    s = "".join(ch for ch in s if not unicodedata.combining(ch))
    s = s.replace("\\", "/")
    s = re.sub(r"\s+", " ", s).strip()
    return s


def _key_token(text):
    s = _normalize(text)
    s = re.sub(r"[^0-9a-z]+", "", s)
    return s


def _safe_name_token(value, fallback="Caja_EMT"):
    txt = _safe_text(value).strip()
    if not txt:
        return fallback
    txt = re.sub(r"[^0-9A-Za-z_]+", "_", txt)
    txt = re.sub(r"_+", "_", txt).strip("_")
    return txt or fallback


def _split_suffix_digits(key):
    m = re.match(r"^(.*?)(\d+)$", _safe_text(key))
    if m:
        return m.group(1), m.group(2)
    return _safe_text(key), ""


def _keys_compatible(target_key, own_key):
    if (not target_key) or (not own_key):
        return False
    if target_key == own_key:
        return True
    t_base, t_suf = _split_suffix_digits(target_key)
    o_base, o_suf = _split_suffix_digits(own_key)
    if t_base and (t_base == o_base):
        if (not t_suf and o_suf) or (t_suf and not o_suf):
            return True
    return False


def _is_group(obj):
    try:
        if obj and obj.isDerivedFrom("App::DocumentObjectGroup"):
            return True
    except Exception:
        pass
    try:
        if obj and obj.isDerivedFrom("App::Part"):
            return True
    except Exception:
        pass
    try:
        if obj and obj.isDerivedFrom("App::Link"):
            return False
    except Exception:
        pass
    return bool(obj and hasattr(obj, "Group"))


def _is_doc_object(obj):
    if obj is None:
        return False
    if isinstance(obj, str):
        return False
    if not hasattr(obj, "TypeId"):
        return False
    return True


def _is_link(obj):
    try:
        return bool(obj and obj.isDerivedFrom("App::Link"))
    except Exception:
        return False


def _linked_object(obj):
    if obj is None:
        return None
    for attr in ("LinkedObject", "Link"):
        try:
            ref = getattr(obj, attr, None)
            if ref is not None:
                return ref
        except Exception:
            pass
    return None


def _as_group_obj(obj):
    if _is_group(obj):
        return obj
    ref = _linked_object(obj)
    if _is_group(ref):
        return ref
    return None


def _is_component_library_group(group_obj):
    txt = f"{_safe_text(getattr(group_obj, 'Label', ''))} {_safe_text(getattr(group_obj, 'Name', ''))}"
    n = _normalize(txt)
    if not n:
        return False
    if "componente" in n:
        return True
    if n.startswith("_lib") or "/_lib" in n or " _lib" in n:
        return True
    return False


def _obj_disp_name(obj, fallback="Objeto"):
    if not _is_doc_object(obj):
        return _safe_text(obj) or fallback
    return _safe_text(getattr(obj, "Label", "")) or _safe_text(getattr(obj, "Name", fallback)) or fallback


def _iter_doc_groups(doc):
    for obj in (doc.Objects or []):
        if _is_group(obj):
            yield obj


def _find_parent_group_linear(doc, obj):
    for grp in _iter_doc_groups(doc):
        try:
            if obj in (getattr(grp, "Group", []) or []):
                return grp
        except Exception:
            continue
    return None


def _parent_group(doc, obj):
    gp = getattr(obj, "getParentGroup", None)
    if callable(gp):
        try:
            p = gp()
            if p:
                return p
        except Exception:
            pass
    return _find_parent_group_linear(doc, obj)


def _group_chain_topdown(doc, obj, max_depth=50):
    chain = []
    seen = set()
    cur = _parent_group(doc, obj)
    while cur is not None and len(chain) < max_depth:
        gid = getattr(cur, "Name", None) or id(cur)
        if gid in seen:
            break
        seen.add(gid)
        chain.append(cur)
        cur = _parent_group(doc, cur)
    chain.reverse()
    return chain


def _contains_any(text, tokens):
    n = _normalize(text)
    if not n:
        return False
    return any(t in n for t in tokens)


def _is_connection_group_label(group_obj):
    txt = f"{_safe_text(getattr(group_obj, 'Label', ''))} {_safe_text(getattr(group_obj, 'Name', ''))}"
    n = _normalize(txt)
    if "conexion" in n or "conexiones" in n:
        return True
    return any(_normalize(lb) in n for lb in LEGACY_CONEX_LABELS)


def _is_bucket_group_label(group_obj):
    txt = f"{_safe_text(getattr(group_obj, 'Label', ''))} {_safe_text(getattr(group_obj, 'Name', ''))}"
    n = _normalize(txt)
    if not n:
        return False
    for token in SKIP_CONTAINER_HINTS:
        if token in n:
            return True
    return False


def _is_device_bucket_group_label(group_obj):
    txt = f"{_safe_text(getattr(group_obj, 'Label', ''))} {_safe_text(getattr(group_obj, 'Name', ''))}"
    return _contains_any(txt, DEVICE_BUCKET_HINTS)


def _is_iluminacion_group(group_obj):
    txt = f"{_safe_text(getattr(group_obj, 'Label', ''))} {_safe_text(getattr(group_obj, 'Name', ''))}"
    return "iluminacion" in _normalize(txt)


def _is_root_device_group(group_obj):
    txt = f"{_safe_text(getattr(group_obj, 'Label', ''))} {_safe_text(getattr(group_obj, 'Name', ''))}"
    n = _normalize(txt)
    return ("tomacorr" in n) or ("apagador" in n)


def _group_chain_has_functional_root(chain):
    for grp in (chain or []):
        if _is_iluminacion_group(grp) or _is_root_device_group(grp):
            return True
    return False


def _chain_has_component_library(chain):
    for grp in (chain or []):
        if _is_component_library_group(grp):
            return True
    return False


def _group_matches_label(group_obj, label):
    tk = _key_token(label)
    if not tk:
        return False
    lk = _key_token(getattr(group_obj, "Label", ""))
    nk = _key_token(getattr(group_obj, "Name", ""))
    return _keys_compatible(tk, lk) or _keys_compatible(tk, nk)


def _find_child_group_flexible(parent, label):
    if parent is None:
        return None
    for child in (getattr(parent, "Group", []) or []):
        grp = _as_group_obj(child)
        if grp is None:
            continue
        if _group_matches_label(grp, label):
            return grp
    return None


def _unique_doc_name(doc, base_name):
    name = _safe_name_token(base_name, "obj")
    if doc.getObject(name) is None:
        return name
    i = 2
    while True:
        cand = f"{name}_{i:02d}"
        if doc.getObject(cand) is None:
            return cand
        i += 1


def _ensure_group(doc, parent, label, prefix):
    if parent is None:
        for grp in _iter_doc_groups(doc):
            if _group_matches_label(grp, label):
                return grp
        name = _unique_doc_name(doc, f"{prefix}_{_safe_name_token(label, 'grupo')}")
        grp = doc.addObject("App::DocumentObjectGroup", name)
        try:
            grp.Label = _safe_text(label).strip() or "Grupo"
        except Exception:
            pass
        return grp

    hit = _find_child_group_flexible(parent, label)
    if hit is not None:
        return hit

    name = _unique_doc_name(doc, f"{prefix}_{_safe_name_token(label, 'grupo')}")
    grp = doc.addObject("App::DocumentObjectGroup", name)
    try:
        grp.Label = _safe_text(label).strip() or "Grupo"
    except Exception:
        pass
    try:
        parent.addObject(grp)
    except Exception:
        pass
    return grp


def _remove_from_all_groups(doc, obj, keep_group=None):
    for grp in _iter_doc_groups(doc):
        if keep_group is not None and grp == keep_group:
            continue
        try:
            if obj in (getattr(grp, "Group", []) or []):
                grp.removeObject(obj)
        except Exception:
            continue


def _resolve_container_group(doc, src_obj):
    chain = _group_chain_topdown(doc, src_obj)
    if not chain:
        return None

    # Prioridad: estructura Iluminacion/Circuito/Recinto.
    ilum_idx = None
    for i, grp in enumerate(chain):
        if _is_iluminacion_group(grp):
            ilum_idx = i
            break
    if ilum_idx is not None:
        tail = []
        for grp in chain[ilum_idx + 1:]:
            if _is_connection_group_label(grp):
                continue
            if _is_bucket_group_label(grp):
                continue
            if _is_device_bucket_group_label(grp):
                continue
            tail.append(grp)
        if len(tail) >= 2:
            return tail[1]  # Recinto
        if len(tail) == 1:
            return tail[0]  # Circuito

    # Prioridad secundaria: Tomacorrientes/Apagadores/<Circuito>/...
    root_idx = None
    for i, grp in enumerate(chain):
        if _is_root_device_group(grp):
            root_idx = i
            break
    if root_idx is not None:
        tail = []
        for grp in chain[root_idx + 1:]:
            if _is_connection_group_label(grp):
                continue
            if _is_bucket_group_label(grp):
                continue
            tail.append(grp)
        if tail:
            return tail[-1]

    # No usar componentes de biblioteca como contenedor funcional.
    if _chain_has_component_library(chain) and (not _group_chain_has_functional_root(chain)):
        return None

    # Fallback: grupo ascendente mas cercano que no sea tecnico.
    for grp in reversed(chain):
        if _is_connection_group_label(grp):
            continue
        if _is_bucket_group_label(grp):
            continue
        if _is_component_library_group(grp):
            continue
        return grp
    return None


def _lineage_objects(doc, obj, max_depth=48):
    out = []
    seen = set()
    cur = obj
    depth = 0
    while cur is not None and depth < max_depth:
        key = getattr(cur, "Name", None) or id(cur)
        if key in seen:
            break
        seen.add(key)
        out.append(cur)
        cur = _parent_group(doc, cur)
        depth += 1
    return out


def _pick_point_from_selection_ex(sel_ex):
    if sel_ex is None:
        return None
    try:
        pts = getattr(sel_ex, "PickedPoints", None) or []
        if pts:
            p = pts[0]
            return App.Vector(float(p.x), float(p.y), float(p.z))
    except Exception:
        pass
    return None


def _doc_object_from_selection_name(doc, raw_name):
    if doc is None:
        return None
    txt = _safe_text(raw_name).strip()
    if not txt:
        return None

    names = []

    def _add_name(value):
        nm = _safe_text(value).strip()
        if not nm or (nm in names):
            return
        names.append(nm)

    _add_name(txt)
    for sep in ("#", ":", "/"):
        if sep in txt:
            _add_name(txt.split(sep)[-1])
    if "." in txt:
        _add_name(txt.split(".", 1)[0])

    i = 0
    while i < len(names):
        nm = names[i]
        i += 1
        for sep in ("#", ":", "/"):
            if sep in nm:
                _add_name(nm.split(sep)[-1])
        if "." in nm:
            _add_name(nm.split(".", 1)[0])

    for nm in names:
        try:
            obj = doc.getObject(nm)
        except Exception:
            obj = None
        if _is_doc_object(obj):
            return obj
    return None


def _selection_ex_doc_objects(doc, sel_ex):
    if doc is None or sel_ex is None:
        return []
    out = []
    seen = set()

    def _push(obj):
        if not _is_doc_object(obj):
            return
        key = getattr(obj, "Name", None) or id(obj)
        if key in seen:
            return
        seen.add(key)
        out.append(obj)

    obj_name = _safe_text(getattr(sel_ex, "ObjectName", "")).strip()
    _push(_doc_object_from_selection_name(doc, obj_name))
    _push(getattr(sel_ex, "Object", None))

    try:
        sub_names = list(getattr(sel_ex, "SubElementNames", []) or [])
    except Exception:
        sub_names = []
    for sub_name in sub_names:
        sub_txt = _safe_text(sub_name).strip()
        if not sub_txt:
            continue
        _push(_doc_object_from_selection_name(doc, sub_txt))
        _push(_doc_object_from_selection_name(doc, sub_txt.split(".", 1)[0]))

    return out


def _iter_dependency_links(obj):
    seen = set()
    for attr in ("InListRecursive", "InList"):
        try:
            parents = list(getattr(obj, attr, []) or [])
        except Exception:
            parents = []
        for p in parents:
            if not _is_link(p):
                continue
            key = getattr(p, "Name", None) or id(p)
            if key in seen:
                continue
            seen.add(key)
            yield p


def _candidate_link_instances(doc, obj, pick_point=None):
    lineage = _lineage_objects(doc, obj)
    ids = set((getattr(o, "Name", None) or id(o)) for o in lineage)
    scored = []
    seen = set()

    def _score_and_add(cand, pref_bias):
        ckey = getattr(cand, "Name", None) or id(cand)
        if ckey in seen:
            return
        seen.add(ckey)
        chain = _group_chain_topdown(doc, cand)
        if not _group_chain_has_functional_root(chain):
            return
        if _resolve_container_group(doc, cand) is None:
            return
        if pick_point is not None:
            try:
                cp = _object_anchor_world(cand)
                dist = (cp - pick_point).Length
            except Exception:
                dist = 0.0
        else:
            dist = 0.0
        scored.append((float(pref_bias), float(dist), -len(chain), _safe_text(getattr(cand, "Name", "")), cand))

    # Prioridad 1: links ya dependientes del objeto seleccionado.
    for dep_link in _iter_dependency_links(obj):
        _score_and_add(dep_link, -100.0)

    # Prioridad 2: links cuyo LinkedObject coincide con la cadena de padres del objeto.
    for cand in (doc.Objects or []):
        if not _is_link(cand):
            continue
        ref = _linked_object(cand)
        if ref is None:
            continue
        rid = getattr(ref, "Name", None) or id(ref)
        if rid not in ids:
            continue
        _score_and_add(cand, 0.0)

    scored.sort(key=lambda t: (t[0], t[1], t[2], t[3]))
    return [t[4] for t in scored]


def _resolve_selected_instance(doc, obj, pick_point=None):
    if obj is None:
        return None
    if _is_group(obj):
        return obj
    if _is_link(obj):
        return obj

    # Si el objeto es subcomponente de un link (ej. Chamfer/Housing),
    # usar la instancia del link para no trabajar sobre el master.
    cands = _candidate_link_instances(doc, obj, pick_point=pick_point)
    if cands:
        return cands[0]

    chain = _group_chain_topdown(doc, obj)
    if _group_chain_has_functional_root(chain):
        return obj

    if _chain_has_component_library(chain) or (not chain):
        return None
    return obj


def _collect_non_group_children(root_group, out, seen):
    gid = getattr(root_group, "Name", None) or id(root_group)
    if gid in seen:
        return
    seen.add(gid)
    for child in (getattr(root_group, "Group", []) or []):
        if _is_group(child):
            _collect_non_group_children(child, out, seen)
            continue
        if not _is_doc_object(child):
            continue
        cid = getattr(child, "Name", None) or id(child)
        if cid in seen:
            continue
        seen.add(cid)
        out.append(child)


def _selection_objects(doc):
    if not GUI_UP:
        return []

    sel_ex = []
    for args in ((), ("",), ("", 0), ("", 1), ("", 2)):
        try:
            chunk = Gui.Selection.getSelectionEx(*args) or []
        except Exception:
            chunk = []
        if chunk:
            sel_ex.extend(chunk)

    raw = []
    for args in ((), ("",), (getattr(doc, "Name", ""),)):
        try:
            chunk = Gui.Selection.getSelection(*args) or []
        except Exception:
            chunk = []
        if chunk:
            raw.extend(chunk)

    candidates = []
    seen_cands = set()
    for sx in sel_ex:
        pick_pt = _pick_point_from_selection_ex(sx)
        for item in _selection_ex_doc_objects(doc, sx):
            base_key = getattr(item, "Name", None) or id(item)
            if pick_pt is not None:
                pkey = (
                    round(float(pick_pt.x), 3),
                    round(float(pick_pt.y), 3),
                    round(float(pick_pt.z), 3),
                )
            else:
                pkey = None
            # Mantener entradas de la misma geometria cuando cambie el punto pick.
            key = ("SX", base_key, pkey)
            if key in seen_cands:
                continue
            seen_cands.add(key)
            candidates.append((item, pick_pt))
    for item in raw:
        if item is None:
            continue
        base_key = getattr(item, "Name", None) or id(item)
        key = ("RAW", base_key)
        if key in seen_cands:
            continue
        seen_cands.add(key)
        candidates.append((item, None))

    if not candidates:
        for obj in (doc.Objects or []):
            if obj is None:
                continue
            try:
                selected_flag = bool(Gui.Selection.isSelected(doc.Name, obj.Name))
            except Exception:
                selected_flag = False
            if not selected_flag:
                continue
            base_key = getattr(obj, "Name", None) or id(obj)
            key = ("ISSEL", base_key)
            if key in seen_cands:
                continue
            seen_cands.add(key)
            candidates.append((obj, None))

    out = []
    seen = set()
    for item, pick_pt in candidates:
        if item is None:
            continue
        if not _is_doc_object(item):
            continue
        if _is_group(item):
            _collect_non_group_children(item, out, seen)
            continue
        resolved = _resolve_selected_instance(doc, item, pick_point=pick_pt)
        if resolved is None:
            continue
        if not _is_doc_object(resolved):
            continue
        oid = getattr(resolved, "Name", None) or id(resolved)
        if oid in seen:
            continue
        seen.add(oid)
        out.append(resolved)

    result = [o for o in out if o is not None and not _is_group(o)]
    if result:
        return result

    fallback = []
    seen_fb = set()
    for item in raw:
        if item is None or (not _is_doc_object(item)) or _is_group(item):
            continue
        resolved = _resolve_selected_instance(doc, item, pick_point=None) or item
        if resolved is None or (not _is_doc_object(resolved)) or _is_group(resolved):
            continue
        oid = getattr(resolved, "Name", None) or id(resolved)
        if oid in seen_fb:
            continue
        seen_fb.add(oid)
        fallback.append(resolved)
    return fallback


def _as_float(value, default=0.0):
    try:
        if hasattr(value, "Value"):
            return float(value.Value)
        return float(value)
    except Exception:
        return float(default)


def _object_anchor_world(obj):
    # Preferir centro del bounding box del shape.
    try:
        shape = getattr(obj, "Shape", None)
        if shape is not None and not shape.isNull():
            bb = shape.BoundBox
            return App.Vector(
                0.5 * (bb.XMin + bb.XMax),
                0.5 * (bb.YMin + bb.YMax),
                0.5 * (bb.ZMin + bb.ZMax),
            )
    except Exception:
        pass

    # Fallback por placement base.
    try:
        return App.Vector(obj.Placement.Base)
    except Exception:
        return App.Vector(0.0, 0.0, 0.0)


def _closest_point_on_bbox(bb, ref_point):
    if bb is None or ref_point is None:
        return None
    try:
        x = min(max(float(ref_point.x), float(bb.XMin)), float(bb.XMax))
        y = min(max(float(ref_point.y), float(bb.YMin)), float(bb.YMax))
        z = min(max(float(ref_point.z), float(bb.ZMin)), float(bb.ZMax))
        return App.Vector(x, y, z)
    except Exception:
        return None


def _object_connection_point_world(obj, toward_point=None):
    # Use the nearest external point on the object bbox to avoid starting
    # the conduit inside the 3D body.
    try:
        shape = getattr(obj, "Shape", None)
        if shape is not None and (not shape.isNull()):
            bb = shape.BoundBox
            if toward_point is not None:
                p = _closest_point_on_bbox(bb, toward_point)
                if p is not None:
                    return p
            return App.Vector(
                0.5 * (float(bb.XMin) + float(bb.XMax)),
                0.5 * (float(bb.YMin) + float(bb.YMax)),
                0.5 * (float(bb.ZMin) + float(bb.ZMax)),
            )
    except Exception:
        pass
    return _object_anchor_world(obj)


def _object_rotation(obj):
    try:
        return obj.Placement.Rotation
    except Exception:
        return App.Rotation()


def _ensure_electriccr_on_path():
    for mod_name in ("ElectricCR", "electriccr"):
        try:
            importlib.import_module(mod_name)
            return True
        except ImportError:
            pass

    try:
        here = Path(__file__).resolve()
    except Exception:
        here = None

    cands = []
    if here is not None:
        for parent in [here.parent, *here.parents]:
            pkg = parent / "ElectricCR"
            if pkg.is_dir():
                cands.extend([str(pkg.parent), str(pkg)])

    try:
        base = Path(App.getUserAppDataDir())
    except Exception:
        base = Path.home() / "AppData" / "Roaming" / "FreeCAD"

    for folder_name in ("Macro", "Macros"):
        pkg = base / folder_name / "ElectricCR"
        if pkg.is_dir():
            cands.extend([str(pkg.parent), str(pkg)])

    for path in cands:
        if path and path not in sys.path:
            sys.path.insert(0, path)

    importlib.invalidate_caches()
    for mod_name in ("ElectricCR", "electriccr"):
        try:
            importlib.import_module(mod_name)
            return True
        except ImportError:
            pass
    return False


def _import_caja_feature():
    if not _ensure_electriccr_on_path():
        raise RuntimeError("No se pudo resolver el paquete ElectricCR.")

    candidates = (
        "ElectricCR.electriccr.features.caja_emt_octogonal",
        "electriccr.features.caja_emt_octogonal",
    )
    for mod_name in candidates:
        try:
            mod = importlib.import_module(mod_name)
            insert_fn = getattr(mod, "insertar_caja_emt_octogonal_link", None)
            master_fn = getattr(mod, "crear_caja_emt_octogonal_master", None)
            if callable(insert_fn) and callable(master_fn):
                return mod, insert_fn, master_fn
        except Exception:
            pass
    raise RuntimeError("No se pudo importar caja_emt_octogonal.")


def _ensure_property(obj, ptype, pname, pgroup, pdesc):
    try:
        if pname not in getattr(obj, "PropertiesList", []):
            obj.addProperty(ptype, pname, pgroup, pdesc)
    except Exception:
        pass


def _box_ports_world(box):
    raw = _safe_text(getattr(box, "PuertosJSON", "")).strip()
    if not raw:
        return []
    try:
        data = json.loads(raw)
    except Exception:
        return []
    if not isinstance(data, list):
        return []
    out = []
    pl = getattr(box, "Placement", None)
    rot = pl.Rotation if pl is not None else App.Rotation()
    for item in data:
        if not isinstance(item, dict):
            continue
        pos = item.get("position")
        direc = item.get("direction")
        if not isinstance(pos, list) or len(pos) != 3:
            continue
        try:
            lp = App.Vector(float(pos[0]), float(pos[1]), float(pos[2]))
        except Exception:
            continue
        wp = pl.multVec(lp) if pl is not None else lp
        if isinstance(direc, list) and len(direc) == 3:
            try:
                ld = App.Vector(float(direc[0]), float(direc[1]), float(direc[2]))
                wd = rot.multVec(ld)
            except Exception:
                wd = App.Vector(0.0, 0.0, -1.0)
        else:
            wd = App.Vector(0.0, 0.0, -1.0)
        out.append(
            {
                "name": _safe_text(item.get("name", "")),
                "point": wp,
                "dir": wd,
            }
        )
    return out


def _pick_box_entry_port(box, src_point):
    ports = _box_ports_world(box)
    if not ports:
        p = getattr(getattr(box, "Placement", None), "Base", App.Vector(0.0, 0.0, 0.0))
        return App.Vector(float(p.x), float(p.y), float(p.z))

    def score(item):
        p = item["point"]
        dz_rank = float(p.z)
        dx = float(src_point.x - p.x)
        dy = float(src_point.y - p.y)
        dxy = ((dx * dx) + (dy * dy)) ** 0.5
        return (dz_rank, dxy)

    ports_sorted = sorted(ports, key=score)
    return ports_sorted[0]["point"]


def _dedupe_points(points, tol=1e-6):
    out = []
    for p in points:
        if not out:
            out.append(p)
            continue
        q = out[-1]
        dx = float(p.x - q.x)
        dy = float(p.y - q.y)
        dz = float(p.z - q.z)
        if (dx * dx + dy * dy + dz * dz) <= (tol * tol):
            continue
        out.append(p)
    return out


def _make_solid_shape(p0, p1):
    z_step = 40.0
    if float(p1.z) >= float(p0.z):
        z_mid = float(p1.z - z_step)
    else:
        z_mid = float(p1.z + z_step)
    pts = [
        App.Vector(float(p0.x), float(p0.y), float(p0.z)),
        App.Vector(float(p0.x), float(p0.y), z_mid),
        App.Vector(float(p1.x), float(p1.y), z_mid),
        App.Vector(float(p1.x), float(p1.y), float(p1.z)),
    ]
    pts = _dedupe_points(pts)
    if len(pts) < 2:
        return None
    if len(pts) == 2:
        return Part.makeLine(pts[0], pts[1])
    return Part.makePolygon(pts)


def _make_flexible_shape(p0, p1):
    dx = float(p1.x - p0.x)
    dy = float(p1.y - p0.y)
    dz = float(p1.z - p0.z)
    dxy = (dx * dx + dy * dy) ** 0.5
    if dxy <= 1e-6:
        vx, vy = 1.0, 0.0
    else:
        vx, vy = (dx / dxy), (dy / dxy)
    px, py = -vy, vx

    if dxy <= 20.0:
        # Keep spline for near-vertical runs, but with tiny lateral swing so it
        # does not overshoot past the component body.
        amp = min(max(abs(dz) * 0.02, 3.0), 8.0)
    else:
        amp = min(max(dxy * 0.18, 35.0), 120.0)

    c1 = App.Vector(
        float(p0.x + dx * 0.33 + px * amp),
        float(p0.y + dy * 0.33 + py * amp),
        float(p0.z + dz * 0.30),
    )
    c2 = App.Vector(
        float(p0.x + dx * 0.66 - px * amp),
        float(p0.y + dy * 0.66 - py * amp),
        float(p0.z + dz * 0.80),
    )
    pts = [App.Vector(p0), c1, c2, App.Vector(p1)]
    curve = Part.BSplineCurve()
    curve.interpolate(pts)
    return curve.toShape()


def _style_connection(obj, conn_type):
    vo = getattr(obj, "ViewObject", None)
    if vo is None:
        return
    try:
        vo.DisplayMode = "Wireframe"
    except Exception:
        pass
    try:
        vo.LineWidth = 2.0
    except Exception:
        pass
    if conn_type == "EMT_Flexible":
        color = (0.12, 0.64, 0.95)
    else:
        color = (1.0, 0.55, 0.08)
    for attr in ("LineColor", "PointColor", "ShapeColor"):
        try:
            setattr(vo, attr, color)
        except Exception:
            pass


def _create_connection(doc, src_obj, box_obj, p_src, p_box, conn_type):
    if conn_type not in {"EMT_Solido", "EMT_Flexible"}:
        return None
    try:
        if conn_type == "EMT_Flexible":
            shape = _make_flexible_shape(p_src, p_box)
        else:
            shape = _make_solid_shape(p_src, p_box)
    except Exception:
        return None
    if shape is None:
        return None

    name = _unique_doc_name(doc, "EMT_Conexion")
    obj = doc.addObject("Part::Feature", name)
    obj.Shape = shape
    src_lbl = _safe_text(getattr(src_obj, "Label", "")) or _safe_text(getattr(src_obj, "Name", "Objeto"))
    box_lbl = _safe_text(getattr(box_obj, "Label", "")) or _safe_text(getattr(box_obj, "Name", "Caja"))
    try:
        obj.Label = f"{conn_type}: {src_lbl} -> {box_lbl}"
    except Exception:
        pass

    _ensure_property(obj, "App::PropertyString", "TipoConexion", "ElectricCR", "Tipo de conexion")
    _ensure_property(obj, "App::PropertyString", "ConduitType", "ElectricCR", "Tipo de tuberia")
    _ensure_property(obj, "App::PropertyString", "EstadoConexion", "Red", "Estado de conexion")
    _ensure_property(obj, "App::PropertyString", "ObjetoOrigen", "Vinculo", "Name objeto origen")
    _ensure_property(obj, "App::PropertyString", "CajaDestino", "Vinculo", "Name caja destino")
    try:
        obj.TipoConexion = conn_type
    except Exception:
        pass
    try:
        obj.ConduitType = "EMT"
    except Exception:
        pass
    try:
        obj.EstadoConexion = "Conectado"
    except Exception:
        pass
    try:
        obj.ObjetoOrigen = _safe_text(getattr(src_obj, "Name", ""))
    except Exception:
        pass
    try:
        obj.CajaDestino = _safe_text(getattr(box_obj, "Name", ""))
    except Exception:
        pass

    _style_connection(obj, conn_type)
    return obj


def _build_box_placement(point, anchor_local, rotation, z_level):
    p = App.Vector(float(point.x), float(point.y), float(z_level))
    rot = rotation if rotation is not None else App.Rotation()
    base = p - rot.multVec(anchor_local)
    return App.Placement(base, rot)


def _default_cfg():
    ctype = _pref_get_str("tipo_conexion", DEFAULT_CONN)
    if ctype not in {"Sin", "EMT_Solido", "EMT_Flexible"}:
        ctype = DEFAULT_CONN
    return {
        "altura_mm": _pref_get_float("altura_mm", DEFAULT_SNPT),
        "diametro_mm": _pref_get_float("diametro_mm", DEFAULT_DIAMETER),
        "tipo_conexion": ctype,
    }


def _run_dialog():
    cfg = _default_cfg()
    if (not GUI_UP) or (QtWidgets is None):
        return cfg

    parent = None
    try:
        parent = Gui.getMainWindow()
    except Exception:
        parent = None

    dlg = QtWidgets.QDialog(parent)
    dlg.setWindowTitle("Insertar Cajas Octogonales Encima")
    dlg.setMinimumWidth(480)
    dlg.setWindowModality(QtCore.Qt.WindowModal if QtCore else dlg.windowModality())

    info = QtWidgets.QLabel(
        "Inserta una caja EMT octogonal encima de cada objeto seleccionado,\n"
        "y opcionalmente crea conexion EMT al objeto."
    )
    info.setWordWrap(True)
    info.setStyleSheet("color:#4b5563;")

    sp_alt = QtWidgets.QDoubleSpinBox()
    sp_alt.setRange(-5000.0, 20000.0)
    sp_alt.setDecimals(1)
    sp_alt.setSuffix(" mm")
    sp_alt.setValue(float(cfg.get("altura_mm", DEFAULT_SNPT)))

    sp_diam = QtWidgets.QDoubleSpinBox()
    sp_diam.setRange(1.0, 200.0)
    sp_diam.setDecimals(1)
    sp_diam.setSuffix(" mm")
    sp_diam.setValue(float(cfg.get("diametro_mm", DEFAULT_DIAMETER)))

    cb_conn = QtWidgets.QComboBox()
    cb_conn.addItem("Sin conexion", "Sin")
    cb_conn.addItem("EMT Solido", "EMT_Solido")
    cb_conn.addItem("EMT Flexible", "EMT_Flexible")
    idx = cb_conn.findData(str(cfg.get("tipo_conexion", DEFAULT_CONN)))
    cb_conn.setCurrentIndex(idx if idx >= 0 else 1)

    frm = QtWidgets.QFormLayout()
    frm.addRow("Altura octogonal (SNPT):", sp_alt)
    frm.addRow("Diametro EMT:", sp_diam)
    frm.addRow("Conexion:", cb_conn)

    btns = QtWidgets.QDialogButtonBox(QtWidgets.QDialogButtonBox.Ok | QtWidgets.QDialogButtonBox.Cancel)
    btns.accepted.connect(dlg.accept)
    btns.rejected.connect(dlg.reject)

    lay = QtWidgets.QVBoxLayout(dlg)
    lay.addWidget(info)
    lay.addLayout(frm)
    lay.addWidget(btns)

    if dlg.exec_() != QtWidgets.QDialog.Accepted:
        return None

    cfg["altura_mm"] = float(sp_alt.value())
    cfg["diametro_mm"] = float(sp_diam.value())
    cfg["tipo_conexion"] = _safe_text(cb_conn.currentData()) or "Sin"
    _save_cfg(cfg)
    return cfg


def main():
    doc = App.ActiveDocument
    if doc is None:
        _err("No hay documento activo.")
        return

    selected = _selection_objects(doc)
    if not selected:
        _warn("Seleccione uno o varios objetos.")
        return
    _log(f"Seleccion efectiva: {len(selected)} objetos.")

    cfg = _run_dialog()
    if cfg is None:
        _warn("Operacion cancelada.")
        return

    conn_type = _safe_text(cfg.get("tipo_conexion", "Sin"))
    altura = float(cfg.get("altura_mm", DEFAULT_SNPT))
    diametro = float(cfg.get("diametro_mm", DEFAULT_DIAMETER))
    if abs(altura) <= 1e-6:
        altura = float(DEFAULT_SNPT)
    diametro = max(1.0, float(diametro))

    try:
        _mod, insert_box, create_master = _import_caja_feature()
    except Exception as ex:
        _err(f"No se pudo cargar feature de caja EMT: {ex}")
        return

    try:
        master = create_master(doc=doc, hide_master=True)
        bb = master.Shape.BoundBox
        anchor_local = App.Vector(
            0.5 * (bb.XMin + bb.XMax),
            0.5 * (bb.YMin + bb.YMax),
            0.5 * (bb.ZMin + bb.ZMax),
        )
    except Exception as ex:
        _err(f"No se pudo preparar master de caja EMT: {ex}")
        return

    created_boxes = 0
    created_conn = 0
    skipped = 0
    try:
        doc.openTransaction("ElectricCR: insertar cajas encima de seleccion")
        for src in selected:
            container = _resolve_container_group(doc, src)
            if container is None:
                skipped += 1
                _warn(f"Sin contenedor valido para '{_obj_disp_name(src)}'.")
                continue

            g_cajas = _ensure_group(doc, container, "Cajas_Octogonales", "CajaOct")
            g_conex = None
            if conn_type in {"EMT_Solido", "EMT_Flexible"}:
                g_conex = _ensure_group(doc, container, "Conexiones_3D", "Conex3D")

            p_src = _object_anchor_world(src)
            rot = _object_rotation(src)
            placement = _build_box_placement(p_src, anchor_local, rot, altura)
            src_label = _safe_text(getattr(src, "Label", "")) or _safe_text(getattr(src, "Name", "Objeto"))

            box = insert_box(
                doc=doc,
                name_prefix=f"{NAME_PREFIX} - {src_label}",
                placement=placement,
                diametro_emt=diametro,
                recompute=False,
                hide_master=True,
            )

            _ensure_property(box, "App::PropertyFloat", "NivelSNPT", "Red", "Cota SNPT objetivo (mm)")
            _ensure_property(box, "App::PropertyString", "EstadoConexion", "Red", "Estado de conexion")
            _ensure_property(box, "App::PropertyString", "ReferenciaObjetoName", "Vinculo", "Objeto de referencia")
            _ensure_property(box, "App::PropertyString", "ReferenciaObjetoLabel", "Vinculo", "Etiqueta objeto referencia")
            try:
                box.NivelSNPT = float(altura)
            except Exception:
                pass
            try:
                box.EstadoConexion = "Conectado" if conn_type in {"EMT_Solido", "EMT_Flexible"} else "Pendiente"
            except Exception:
                pass
            try:
                box.ReferenciaObjetoName = _safe_text(getattr(src, "Name", ""))
            except Exception:
                pass
            try:
                box.ReferenciaObjetoLabel = _safe_text(getattr(src, "Label", ""))
            except Exception:
                pass

            _remove_from_all_groups(doc, box, keep_group=g_cajas)
            try:
                g_cajas.addObject(box)
            except Exception:
                pass
            created_boxes += 1

            if g_conex is not None:
                p_box = _pick_box_entry_port(box, p_src)
                p_src_conn = _object_connection_point_world(src, toward_point=p_box)
                conn_obj = _create_connection(doc, src, box, p_src_conn, p_box, conn_type)
                if conn_obj is not None:
                    _remove_from_all_groups(doc, conn_obj, keep_group=g_conex)
                    try:
                        g_conex.addObject(conn_obj)
                    except Exception:
                        pass
                    created_conn += 1

            _log(
                f"Caja creada: {box.Label} | contenedor={_obj_disp_name(container, 'Grupo')} "
                f"| altura={altura:.1f} mm | conexion={conn_type}"
            )

        doc.recompute()
        doc.commitTransaction()
    except Exception as ex:
        try:
            doc.abortTransaction()
        except Exception:
            pass
        _err(f"Fallo general: {ex}")
        return

    _log(
        f"Finalizado. Seleccion={len(selected)} | cajas={created_boxes} | conexiones={created_conn} | omitidos={skipped}."
    )


if __name__ == "__main__":
    main()

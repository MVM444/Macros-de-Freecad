# -*- coding: utf-8 -*-
# Macro: RectFromBoundaryLines
# Description: Crea un rectangulo Draft desde aristas o caras seleccionadas de muros BIM.
# FreeCAD: 1.1.3
# Date: 2026-08-10 20:06 CST

import math

import Draft
import FreeCAD
import FreeCADGui
import Part
from FreeCAD import Placement, Rotation, Vector


XY_TOL = 1e-6
VERTICAL_FACE_MAX_Z = 0.20


def debug(msg):
    FreeCAD.Console.PrintMessage("[RectFromBoundaryLines] DEBUG: {}\n".format(msg))


def warn(msg):
    FreeCAD.Console.PrintWarning("[RectFromBoundaryLines] {}\n".format(msg))


def add_prop(obj, typ, name_, group, desc):
    try:
        if not hasattr(obj, name_):
            obj.addProperty(typ, name_, group, desc)
    except Exception:
        pass


def label(obj):
    return str(getattr(obj, "Label", "") or getattr(obj, "Name", "") or "")


def is_group(obj):
    return hasattr(obj, "Group")


def ensure_areas_group(doc):
    for obj in doc.Objects:
        if is_group(obj) and label(obj).strip().lower() == "areas":
            return obj
    group = doc.addObject("App::DocumentObjectGroup", "Areas")
    group.Label = "Areas"
    return group


def next_area_label(doc):
    existing = set(label(obj) for obj in doc.Objects)
    idx = 1
    while True:
        candidate = "Area_{:03d}".format(idx)
        if candidate not in existing:
            return candidate
        idx += 1


def _text_property(obj, name):
    try:
        return str(getattr(obj, name, "") or "").strip().lower()
    except Exception:
        return ""


def is_bim_wall(obj):
    """Recognize native Arch/BIM walls and ElectricCR/FacilArquitectura wall roles."""
    if obj is None:
        return False
    if _text_property(obj, "FA_Role") == "wall":
        return True
    if _text_property(obj, "IfcType") in ("wall", "wallstandardcase"):
        return True
    try:
        proxy_type = str(getattr(getattr(obj, "Proxy", None), "Type", "") or "").lower()
        if proxy_type == "wall":
            return True
    except Exception:
        pass
    type_id = _text_property(obj, "TypeId")
    if "arch::wall" in type_id:
        return True
    return False


def configure_area_rectangle(obj, width, height, group, source_walls=None, source_method="selected_edges"):
    area_m2 = (float(width) * float(height)) / 1000000.0
    obj.Label = next_area_label(FreeCAD.ActiveDocument)
    add_prop(obj, "App::PropertyString", "ElectricCRTipo", "ElectricCR", "Tipo logico")
    add_prop(obj, "App::PropertyString", "GeneratedBy", "ElectricCR", "Macro generadora")
    add_prop(obj, "App::PropertyFloat", "AreaM2", "ElectricCR", "Area en m2")
    add_prop(obj, "App::PropertyInteger", "VirtualClosures", "ElectricCR", "Cierres virtuales")
    add_prop(obj, "App::PropertyFloat", "Confidence", "ElectricCR", "Confianza")
    add_prop(obj, "App::PropertyString", "FA_SourceMethod", "FacilArquitectura", "Metodo de origen")
    add_prop(obj, "App::PropertyLinkList", "FA_SourceWalls", "FacilArquitectura", "Muros BIM fuente")
    try:
        obj.ElectricCRTipo = "Area"
        obj.GeneratedBy = "RectFromBoundaryLines"
        obj.AreaM2 = area_m2
        obj.VirtualClosures = 0
        obj.Confidence = 0.95
        obj.FA_SourceMethod = str(source_method or "selected_edges")
        obj.FA_SourceWalls = list(source_walls or [])
    except Exception:
        pass
    try:
        if hasattr(obj, "MakeFace"):
            obj.MakeFace = True
    except Exception:
        pass
    try:
        group.addObject(obj)
    except Exception:
        pass
    try:
        # Tono parecido al de AreaPorClick, pero mas verde-azulado para distinguir origen manual.
        obj.ViewObject.LineColor = (0.0, 0.48, 0.42)
        obj.ViewObject.ShapeColor = (0.35, 0.80, 0.70)
        obj.ViewObject.Transparency = 72
    except Exception:
        pass
    return area_m2


def _xy_point(point):
    return Vector(float(point.x), float(point.y), 0.0)


def _straight_xy_endpoints(edge):
    try:
        if len(edge.Vertexes) < 2:
            return None
        p1 = _xy_point(edge.Vertexes[0].Point)
        p2 = _xy_point(edge.Vertexes[-1].Point)
        chord = p1.distanceToPoint(p2)
        if chord <= XY_TOL:
            return None
        # A straight edge has the same 3D chord and curve length. This rejects arcs.
        chord_3d = edge.Vertexes[0].Point.distanceToPoint(edge.Vertexes[-1].Point)
        if abs(float(edge.Length) - chord_3d) > max(0.05, chord_3d * 1e-5):
            return None
        return p1, p2
    except Exception:
        return None


def _make_xy_line(p1, p2):
    p1 = _xy_point(p1)
    p2 = _xy_point(p2)
    if p1.distanceToPoint(p2) <= XY_TOL:
        return None
    return Part.makeLine(p1, p2)


def _face_normal(face):
    try:
        u0, u1, v0, v1 = face.ParameterRange
        normal = face.normalAt((u0 + u1) * 0.5, (v0 + v1) * 0.5)
    except Exception:
        try:
            normal = face.normalAt(0.0, 0.0)
        except Exception:
            return None
    if normal.Length <= XY_TOL:
        return None
    return normal.normalize()


def _distance_point_to_segment_xy(point, p1, p2):
    point = _xy_point(point)
    p1 = _xy_point(p1)
    p2 = _xy_point(p2)
    delta = p2.sub(p1)
    length_sq = delta.dot(delta)
    if length_sq <= XY_TOL:
        return point.distanceToPoint(p1)
    t = max(0.0, min(1.0, point.sub(p1).dot(delta) / length_sq))
    return point.distanceToPoint(p1 + delta * t)


def _vertical_face_to_xy_line(face, normal):
    """Project the plane of a vertical wall face to one supporting line in XY."""
    horizontal_normal = Vector(normal.x, normal.y, 0.0)
    if horizontal_normal.Length <= XY_TOL:
        return None
    horizontal_normal.normalize()
    direction = Vector(-horizontal_normal.y, horizontal_normal.x, 0.0)
    points = [_xy_point(vertex.Point) for vertex in face.Vertexes]
    if len(points) < 2:
        return None
    plane_c = horizontal_normal.dot(points[0])
    coords = [direction.dot(point) for point in points]
    p1 = horizontal_normal * plane_c + direction * min(coords)
    p2 = horizontal_normal * plane_c + direction * max(coords)
    return _make_xy_line(p1, p2)


def _nearest_face_boundary_line(face, picked_point=None):
    candidates = []
    for edge in face.Edges:
        endpoints = _straight_xy_endpoints(edge)
        if endpoints is None:
            continue
        p1, p2 = endpoints
        candidates.append((p1.distanceToPoint(p2), p1, p2))
    if not candidates:
        return None
    if picked_point is not None:
        candidates.sort(key=lambda item: _distance_point_to_segment_xy(picked_point, item[1], item[2]))
    else:
        candidates.sort(key=lambda item: item[0], reverse=True)
        warn("La cara horizontal no incluyo punto de seleccion; se uso su borde recto mas largo.")
    return _make_xy_line(candidates[0][1], candidates[0][2])


def face_to_boundary_line(face, picked_point=None):
    """Convert a selected BIM wall face into one unambiguous XY boundary line."""
    normal = _face_normal(face)
    if normal is None:
        return None, "sin_normal"
    if abs(normal.z) <= VERTICAL_FACE_MAX_Z:
        return _vertical_face_to_xy_line(face, normal), "cara_vertical"
    return _nearest_face_boundary_line(face, picked_point), "borde_cara_horizontal"


def _picked_point_for(entry, index):
    points = list(getattr(entry, "PickedPoints", []) or [])
    if not points:
        return None
    if index < len(points):
        return points[index]
    return points[0]


def get_selected_boundaries(selection_ex=None):
    """Return selected straight edges plus boundary lines derived from BIM wall faces."""
    if selection_ex is None:
        selection_ex = FreeCADGui.Selection.getSelectionEx()
    edges = []
    source_walls = []
    explicit_count = 0
    face_count = 0
    ignored_faces = 0
    methods = set()

    for entry in selection_ex:
        obj = getattr(entry, "Object", None)
        names = list(getattr(entry, "SubElementNames", []) or [])
        subobjects = list(getattr(entry, "SubObjects", []) or [])
        for index, sub_name in enumerate(names):
            try:
                subobject = subobjects[index] if index < len(subobjects) else obj.Shape.getElement(sub_name)
            except Exception:
                continue
            if str(sub_name).startswith("Edge"):
                endpoints = _straight_xy_endpoints(subobject)
                if endpoints is not None:
                    edges.append(_make_xy_line(endpoints[0], endpoints[1]))
                    explicit_count += 1
                    methods.add("selected_edges")
                continue
            if not str(sub_name).startswith("Face"):
                continue
            if not is_bim_wall(obj):
                ignored_faces += 1
                warn("Se ignoro {} de {} porque el objeto no se reconoce como muro BIM.".format(sub_name, label(obj)))
                continue
            boundary, method = face_to_boundary_line(subobject, _picked_point_for(entry, index))
            if boundary is None:
                ignored_faces += 1
                warn("No se pudo obtener una linea limite de {} en {}.".format(sub_name, label(obj)))
                continue
            edges.append(boundary)
            face_count += 1
            methods.add(method)
            if obj not in source_walls:
                source_walls.append(obj)

    debug(
        "Limites: {} aristas, {} caras BIM convertidas, {} caras omitidas".format(
            explicit_count, face_count, ignored_faces
        )
    )
    return edges, source_walls, "+".join(sorted(methods)) or "selected_edges"


def get_selected_edges(selection_ex=None):
    """Compatibility helper retained for callers that only expect the edge list."""
    return get_selected_boundaries(selection_ex)[0]


def cluster_directions(edges):
    dirs = []
    for edge in edges:
        endpoints = _straight_xy_endpoints(edge)
        if endpoints is None:
            continue
        p1, p2 = endpoints
        direction = p2.sub(p1)
        if direction.Length <= XY_TOL:
            continue
        direction.normalize()
        if direction.x < 0 or (abs(direction.x) < XY_TOL and direction.y < 0):
            direction = -direction
        dirs.append((direction, edge))
    clusters = []
    for direction, edge in dirs:
        placed = False
        for cluster in clusters:
            if abs(cluster["dir"].dot(direction)) > 0.99:
                cluster["edges"].append((direction, edge))
                placed = True
                break
        if not placed:
            clusters.append({"dir": direction, "edges": [(direction, edge)]})
    clusters.sort(key=lambda item: len(item["edges"]), reverse=True)
    debug("Clusters: {} sizes {}".format(len(clusters), [len(item["edges"]) for item in clusters]))
    return clusters


def intersect(n1, c1, n2, c2):
    det = n1.x * n2.y - n1.y * n2.x
    if abs(det) < XY_TOL:
        return None
    x = (c1 * n2.y - n1.y * c2) / det
    y = (n1.x * c2 - c1 * n2.x) / det
    return Vector(x, y, 0)


def compute_boundaries(cluster):
    direction = cluster["dir"]
    normal = Vector(-direction.y, direction.x, 0).normalize()
    values = []
    for unused_direction, edge in cluster["edges"]:
        point = edge.Vertexes[0].Point
        values.append(normal.dot(_xy_point(point)))
    return normal, min(values), max(values)


def rectangle_points_from_edges(edges):
    clusters = cluster_directions(edges)
    if not clusters:
        raise RuntimeError("La seleccion no contiene limites lineales validos en planta.")

    points = []
    if len(clusters) >= 2:
        debug("Usando 2 orientaciones para calcular limites")
        n1, c1min, c1max = compute_boundaries(clusters[0])
        n2, c2min, c2max = compute_boundaries(clusters[1])
        for c1 in (c1min, c1max):
            for c2 in (c2min, c2max):
                point = intersect(n1, c1, n2, c2)
                if point:
                    points.append(point)
    else:
        debug("Fallback orientado: infiriendo rectangulo de puntos extremos")
        axis = clusters[0]["dir"]
        perpendicular = Vector(-axis.y, axis.x, 0)
        endpoints = []
        for edge in edges:
            straight = _straight_xy_endpoints(edge)
            if straight is not None:
                endpoints.extend(straight)
        if len(endpoints) < 2:
            raise RuntimeError("No hay suficientes extremos validos para inferir el rectangulo.")
        reference = endpoints[0]
        coordinates = [((point - reference).dot(axis), (point - reference).dot(perpendicular)) for point in endpoints]
        xs = [item[0] for item in coordinates]
        ys = [item[1] for item in coordinates]
        points = [
            reference + axis * x + perpendicular * y
            for x in (min(xs), max(xs))
            for y in (min(ys), max(ys))
        ]

    if len(points) != 4:
        raise RuntimeError("No se generaron cuatro vertices; se encontraron {}.".format(len(points)))
    center = sum(points, Vector(0, 0, 0)) * 0.25
    points.sort(key=lambda point: math.atan2(point.y - center.y, point.x - center.x))
    return points


def create_rectangle_from_edges(doc, edges, source_walls=None, source_method="selected_edges"):
    points = rectangle_points_from_edges(edges)
    debug("Vertices: {}".format([tuple(point) for point in points]))

    width_vector = points[1].sub(points[0])
    height_vector = points[3].sub(points[0])
    width = width_vector.Length
    height = height_vector.Length
    if width <= XY_TOL or height <= XY_TOL:
        raise RuntimeError("El rectangulo calculado tiene ancho o alto nulo.")
    angle = math.degrees(math.atan2(width_vector.y, width_vector.x))
    placement = Placement(points[0], Rotation(Vector(0, 0, 1), angle))
    debug(
        "Origin={}, width={:.3f}, height={:.3f}, angle={:.3f}".format(
            tuple(points[0]), width, height, angle
        )
    )

    group = ensure_areas_group(doc)
    doc.openTransaction("ElectricCR: crear rectangulo desde limites")
    try:
        obj = Draft.makeRectangle(width, height, placement)
        if obj is None:
            raise RuntimeError("Draft.makeRectangle no devolvio objeto")
        area_m2 = configure_area_rectangle(obj, width, height, group, source_walls, source_method)
        doc.commitTransaction()
    except Exception:
        try:
            doc.abortTransaction()
        except Exception:
            pass
        raise
    doc.recompute()
    return obj, area_m2


def RectFromBoundaryLines(selection_ex=None):
    doc = FreeCAD.ActiveDocument
    if doc is None:
        FreeCAD.Console.PrintError("No hay documento activo.\n")
        return None
    edges, source_walls, source_method = get_selected_boundaries(selection_ex)
    if len(edges) < 2:
        FreeCAD.Console.PrintError(
            "Seleccione al menos dos aristas lineales o caras de muros BIM que definan limites.\n"
        )
        return None
    try:
        obj, area_m2 = create_rectangle_from_edges(doc, edges, source_walls, source_method)
    except Exception as exc:
        FreeCAD.Console.PrintError("[RectFromBoundaryLines] Error: {}\n".format(exc))
        return None
    FreeCAD.Console.PrintMessage(
        "[RectFromBoundaryLines] Creada {}: {:.2f} m2 en grupo Areas; origen {}.\n".format(
            obj.Label, area_m2, source_method
        )
    )
    return obj


if __name__ == "__main__":
    RectFromBoundaryLines()

# Icon: conectar_objetos_por_bordes_WIRE.svg

import FreeCAD
import FreeCADGui
import Part
import Draft
import os
import sys
_THIS_DIR = os.path.dirname(__file__) if '__file__' in globals() else ''
if _THIS_DIR and _THIS_DIR not in sys.path:
    sys.path.insert(0, _THIS_DIR)
import importlib
import conexiones_grouping as _conexiones_grouping_mod
_conexiones_grouping_mod = importlib.reload(_conexiones_grouping_mod)
ensure_conexiones_group = _conexiones_grouping_mod.ensure_conexiones_group
def conectar_objetos_por_bordes():
    doc = FreeCAD.ActiveDocument
    selected_objects = FreeCADGui.Selection.getSelectionEx()

    if len(selected_objects) < 2:
        FreeCAD.Console.PrintError("Debe seleccionar al menos dos objetos y los puntos correspondientes (vÃƒÂ©rtices o bordes).\n")
        return

    # Identificar el grupo padre de los objetos seleccionados
    grupo_padre = None
    for obj in doc.Objects:
        if obj.TypeId == 'App::DocumentObjectGroup' and all(sel_obj.Object in obj.Group for sel_obj in selected_objects):
            grupo_padre = obj
            break

    if grupo_padre:
        FreeCAD.Console.PrintMessage(f"Grupo padre encontrado: {grupo_padre.Name}\n")
    else:
        FreeCAD.Console.PrintWarning("Sin grupo comun; se usara Conexiones_Huerfanas.\n")

    conexiones_grupo = ensure_conexiones_group(
        doc,
        parent_group=grupo_padre,
        objects=[sel.Object for sel in selected_objects if getattr(sel, "Object", None)],
    )

    # Diccionario para rastrear conexiones
    conexiones_realizadas = set()

    # FunciÃƒÂ³n para obtener el punto medio del borde seleccionado
    def obtener_punto_y_direccion_borde(selection_detail):
        if selection_detail.HasSubObjects:
            for sub_obj in selection_detail.SubObjects:
                if isinstance(sub_obj, Part.Edge):
                    punto_medio = sub_obj.CenterOfMass if hasattr(sub_obj, 'CenterOfMass') else sub_obj.Curve.value(0.5)
                    tangente = sub_obj.tangentAt(0.5)

                    # Normalizar y obtener direcciÃƒÂ³n perpendicular
                    if abs(tangente.x) > abs(tangente.y):
                        direccion_perpendicular = FreeCAD.Vector(0, 1, 0) * 20
                    else:
                        direccion_perpendicular = FreeCAD.Vector(1, 0, 0) * 20

                    return punto_medio, direccion_perpendicular
        return selection_detail.Object.Shape.BoundBox.Center, None

    # Obtener los puntos seleccionados
    puntos_seleccionados = []
    for selection_detail in selected_objects:
        punto, direccion = obtener_punto_y_direccion_borde(selection_detail)
        puntos_seleccionados.append((selection_detail.Object, punto, direccion))

    if len(puntos_seleccionados) < 2:
        FreeCAD.Console.PrintError("No hay suficientes puntos seleccionados para conectar.\n")
        return

    # FunciÃƒÂ³n para dibujar conexiones ortogonales
    def dibujar_conexiones(puntos):
        for i in range(len(puntos) - 1):
            objeto1, punto1, direccion1 = puntos[i]
            objeto2, punto2, direccion2 = puntos[i + 1]

            if (objeto1.Name, objeto2.Name) in conexiones_realizadas or (objeto2.Name, objeto1.Name) in conexiones_realizadas:
                continue

            puntos_conexion = [punto1]

            # Agregar puntos intermedios para conexiones ortogonales
            if direccion1 and direccion2:
                intermedio1 = punto1 + direccion1
                puntos_conexion.append(intermedio1)

                if abs(punto1.x - punto2.x) > 1e-3:
                    intermedio2 = FreeCAD.Vector(punto2.x, intermedio1.y, punto1.z)
                    puntos_conexion.append(intermedio2)

                if abs(punto1.y - punto2.y) > 1e-3:
                    intermedio3 = FreeCAD.Vector(punto2.x, punto2.y, punto1.z)
                    puntos_conexion.append(intermedio3)

            puntos_conexion.append(punto2)

            # Crear y almacenar la lÃƒÂ­nea en el grupo de conexiones usando Draft.make_wire()
            linea_obj = Draft.make_wire(puntos_conexion, closed=False)
            linea_obj.Label = f'Conexion_{objeto1.Name}_{objeto2.Name}'
            conexiones_grupo.addObject(linea_obj)

            conexiones_realizadas.add((objeto1.Name, objeto2.Name))

    # Dibujar conexiones
    dibujar_conexiones(puntos_seleccionados)

    # Actualizar el documento
    doc.recompute()

# Ejecutar la funciÃƒÂ³n
conectar_objetos_por_bordes()

# -*- coding: utf-8 -*-
# MenuText: Cambiar altura y rotacion de objetos
# ToolTip: Ajusta altura 3D semantica y rotacion en planta sin elevar simbolos 2D
# Revision: 2026-08-06 13:05 America/Costa_Rica, rev 2
# Transaction: self
#
# Important:
# - ElectricCR direct objects use AlturaRel.
# - ElectricCR App::Link objects are relinked to an immutable height master.
# - MEP HVAC objects use their public installation-elevation API.
# - Only simple fallback objects change Placement.Base.z.
# - Rotation is composed around world Z; technical pitch/roll is preserved.

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

import math
import os
import sys

import FreeCAD as App
import FreeCADGui as Gui


def _ensure_workbench_root_on_path():
    """Expose sibling ElectricCR and MEPWorkbenchCR packages to this macro."""
    try:
        macro_dir = os.path.dirname(os.path.abspath(__file__))
        root = os.path.dirname(macro_dir)
        if os.path.isdir(os.path.join(root, "ElectricCR")) and root not in sys.path:
            sys.path.insert(0, root)
    except Exception:
        pass


_ensure_workbench_root_on_path()

QtWidgets = None
QtCore = None

try:
    from PySide6 import QtWidgets, QtCore  # type: ignore
except Exception:
    try:
        from PySide2 import QtWidgets, QtCore  # type: ignore
    except Exception:
        try:
            from PySide import QtGui as QtWidgets  # type: ignore
            from PySide import QtCore  # type: ignore
        except Exception:
            QtWidgets = None
            QtCore = None


def log_info(msg):
    App.Console.PrintMessage(str(msg) + "\n")


def log_warn(msg):
    App.Console.PrintWarning(str(msg) + "\n")


def log_err(msg):
    App.Console.PrintError(str(msg) + "\n")


def _import_electriccr_api():
    for module_name in (
        "ElectricCR.electriccr.features.objeto_toma_uno",
        "electriccr.features.objeto_toma_uno",
    ):
        try:
            return __import__(module_name, fromlist=["objeto_toma_uno"])
        except Exception:
            continue
    return None


def _import_hvac_api():
    for module_name in (
        "MEPWorkbenchCR.MEP.hvac.hvac_equipment",
        "MEP.hvac.hvac_equipment",
    ):
        try:
            return __import__(module_name, fromlist=["hvac_equipment"])
        except Exception:
            continue
    return None


def _object_key(obj):
    if obj is None:
        return ""
    doc = getattr(obj, "Document", None)
    return "{}:{}".format(
        str(getattr(doc, "Name", "") or ""),
        str(getattr(obj, "Name", "") or id(obj)),
    )


def _selected_compatible(objects=None):
    raw = list(objects if objects is not None else (Gui.Selection.getSelection() or []))
    hvac_api = _import_hvac_api()
    resolved = []
    seen = set()
    for candidate in raw:
        obj = candidate
        if hvac_api is not None:
            try:
                owner = hvac_api.resolve_equipment_owner(candidate, doc=getattr(candidate, "Document", None))
                if owner is not None:
                    obj = owner
            except Exception:
                pass
        if obj is None or not hasattr(obj, "Placement"):
            continue
        key = _object_key(obj)
        if key in seen:
            continue
        resolved.append(obj)
        seen.add(key)
    return resolved


def _yaw_deg(rot):
    if rot is None:
        return 0.0
    try:
        e = rot.toEuler()
        if isinstance(e, (list, tuple)) and len(e) >= 1:
            return float(e[0])
    except Exception:
        pass
    try:
        return math.degrees(float(rot.Angle))
    except Exception:
        return 0.0


def _copy_placement(obj):
    return App.Placement(getattr(obj, "Placement", App.Placement()))


def _rotation_with_world_yaw(rot, mode, value_deg):
    current = App.Rotation(rot)
    current_yaw = _yaw_deg(current)
    if str(mode or "abs") == "delta":
        delta = float(value_deg)
        target = current_yaw + delta
    else:
        target = float(value_deg)
        delta = ((target - current_yaw + 180.0) % 360.0) - 180.0
    z_delta = App.Rotation(App.Vector(0.0, 0.0, 1.0), float(delta))
    return z_delta.multiply(current), current_yaw, target


def _height_adapter(obj):
    hvac_api = _import_hvac_api()
    if hvac_api is not None:
        try:
            if hvac_api.resolve_equipment_owner(obj, doc=getattr(obj, "Document", None)) is obj:
                return "mep_hvac", hvac_api
        except Exception:
            pass

    electriccr_api = _import_electriccr_api()
    if electriccr_api is not None:
        try:
            if electriccr_api.is_electriccr_device(obj):
                kind = "electriccr_link" if str(getattr(obj, "TypeId", "") or "") == "App::Link" else "electriccr_direct"
                return kind, electriccr_api
        except Exception:
            pass
    return "placement", None


def _current_height_mm(obj):
    kind, api = _height_adapter(obj)
    if kind == "mep_hvac":
        return float(api.installation_elevation_mm(obj)), kind
    if kind.startswith("electriccr_"):
        return float(api.installation_elevation_mm(obj)), kind
    return float(obj.Placement.Base.z), kind


def _apply_height(obj, target_mm):
    old_mm, kind = _current_height_mm(obj)
    if kind == "mep_hvac":
        actual = float(_height_adapter(obj)[1].set_installation_elevation(obj, target_mm))
        return old_mm, actual, kind, "InstallationElevation/Height"
    if kind.startswith("electriccr_"):
        result = _height_adapter(obj)[1].set_installation_elevation(obj, target_mm)
        actual = float(result.get("new_mm", target_mm))
        prop = "AlturaRel"
        if kind == "electriccr_link":
            prop = "LinkedObject({}->{})+AlturaRel".format(
                str(result.get("master_old", "") or "?"),
                str(result.get("master_new", "") or "?"),
            )
        return old_mm, actual, kind, prop

    placement = _copy_placement(obj)
    placement.Base.z = float(target_mm)
    obj.Placement = placement
    return old_mm, float(target_mm), kind, "Placement.Base.z"


def _object_label(obj):
    return "{} ({})".format(
        str(getattr(obj, "Label", "") or getattr(obj, "Name", "") or "?"),
        str(getattr(obj, "Name", "") or "?"),
    )


def _run_dialog(dialog):
    fn = getattr(dialog, "exec", None)
    if callable(fn):
        return fn()
    fn = getattr(dialog, "exec_", None)
    if callable(fn):
        return fn()
    return 0


if QtWidgets is not None:
    class CambiarAlturaYRotacionDialogo(QtWidgets.QDialog):
        def __init__(self, parent=None):
            super(CambiarAlturaYRotacionDialogo, self).__init__(parent)
            self.setWindowTitle("Cambiar altura y rotacion")
            self.setMinimumWidth(460)

            layout = QtWidgets.QVBoxLayout(self)

            self.lbl_sel = QtWidgets.QLabel("Seleccion actual: 0 objeto(s) compatible(s)")
            layout.addWidget(self.lbl_sel)

            form = QtWidgets.QFormLayout()

            self.chk_altura = QtWidgets.QCheckBox("Aplicar altura")
            self.chk_altura.setChecked(True)
            self.cmb_modo_altura = QtWidgets.QComboBox()
            self.cmb_modo_altura.addItem("Absoluta (altura de instalacion)", "abs")
            self.cmb_modo_altura.addItem("Delta (+/-)", "delta")
            self.sp_altura = QtWidgets.QDoubleSpinBox()
            self.sp_altura.setDecimals(3)
            self.sp_altura.setRange(-10000000.0, 10000000.0)
            self.sp_altura.setSingleStep(10.0)
            self.sp_altura.setSuffix(" mm")

            self.chk_rot = QtWidgets.QCheckBox("Aplicar rotacion")
            self.chk_rot.setChecked(True)
            self.cmb_modo_rot = QtWidgets.QComboBox()
            self.cmb_modo_rot.addItem("Absoluta (yaw Z)", "abs")
            self.cmb_modo_rot.addItem("Delta (+/-)", "delta")
            self.sp_rot = QtWidgets.QDoubleSpinBox()
            self.sp_rot.setDecimals(2)
            self.sp_rot.setRange(-360000.0, 360000.0)
            self.sp_rot.setSingleStep(5.0)
            self.sp_rot.setSuffix(" deg")

            form.addRow(self.chk_altura)
            form.addRow("Modo altura:", self.cmb_modo_altura)
            form.addRow("Valor altura:", self.sp_altura)
            form.addRow(self.chk_rot)
            form.addRow("Modo rotacion:", self.cmb_modo_rot)
            form.addRow("Valor rotacion:", self.sp_rot)

            layout.addLayout(form)

            self.btns = QtWidgets.QDialogButtonBox(QtWidgets.QDialogButtonBox.Ok | QtWidgets.QDialogButtonBox.Cancel)
            self.btn_apply = self.btns.addButton("Aplicar", QtWidgets.QDialogButtonBox.ApplyRole)
            layout.addWidget(self.btns)

            self.btns.accepted.connect(self._apply_and_accept)
            self.btns.rejected.connect(self.reject)
            self.btn_apply.clicked.connect(self.apply_changes)

            self._preload_selection()

        def _preload_selection(self):
            objs = _selected_compatible()
            n = len(objs)
            self.lbl_sel.setText("Seleccion actual: {} objeto(s) compatible(s)".format(n))
            if not objs:
                return

            avg_z = sum(_current_height_mm(o)[0] for o in objs) / float(n)
            avg_yaw = sum(_yaw_deg(o.Placement.Rotation) for o in objs) / float(n)

            self.sp_altura.setValue(avg_z)
            self.sp_rot.setValue(avg_yaw)

        def _apply_and_accept(self):
            if self.apply_changes():
                self.accept()

        def apply_changes(self):
            return cambiar_altura_y_rotacion_objetos(
                apply_height=bool(self.chk_altura.isChecked()),
                height_mode=str(self.cmb_modo_altura.currentData() or "abs"),
                height_value=float(self.sp_altura.value()),
                apply_rotation=bool(self.chk_rot.isChecked()),
                rotation_mode=str(self.cmb_modo_rot.currentData() or "abs"),
                rotation_value=float(self.sp_rot.value()),
            )


def cambiar_altura_y_rotacion_objetos(
    apply_height,
    height_mode,
    height_value,
    apply_rotation,
    rotation_mode,
    rotation_value,
    objects=None,
):
    objs = _selected_compatible(objects=objects)
    if not objs:
        log_err("[ECR][ALTURA] No hay objetos seleccionados compatibles.")
        return False

    if not apply_height and not apply_rotation:
        log_warn("[ECR][ALTURA] No hay cambios para aplicar.")
        return False

    doc = App.ActiveDocument
    if doc is None:
        log_err("[ECR][ALTURA] No hay documento activo.")
        return False

    foreign_docs = [obj for obj in objs if getattr(obj, "Document", None) is not doc]
    if foreign_docs:
        log_err("[ECR][ALTURA] La seleccion contiene objetos de otro documento.")
        return False

    changed = 0
    skipped = 0

    doc.openTransaction("Cambiar altura y rotacion")
    try:
        for obj in objs:
            try:
                kind, _api = _height_adapter(obj)
                log_info(
                    "[ECR][ALTURA] objeto={} tipo={} TypeId={}".format(
                        _object_label(obj), kind, str(getattr(obj, "TypeId", "") or "?"),
                    )
                )

                object_changed = False
                if apply_height:
                    current_mm, _kind = _current_height_mm(obj)
                    target_mm = current_mm + float(height_value) if height_mode == "delta" else float(height_value)
                    old_mm, new_mm, used_kind, prop = _apply_height(obj, target_mm)
                    log_info(
                        "[ECR][ALTURA] objeto={} estrategia={} propiedad={} anterior={:.3f}mm nueva={:.3f}mm resultado=OK".format(
                            _object_label(obj), used_kind, prop, old_mm, new_mm,
                        )
                    )
                    object_changed = True

                if apply_rotation:
                    placement = _copy_placement(obj)
                    new_rot, old_yaw, _target_yaw = _rotation_with_world_yaw(
                        placement.Rotation, rotation_mode, rotation_value,
                    )
                    placement.Rotation = new_rot
                    obj.Placement = placement
                    log_info(
                        "[ECR][ROTACION] objeto={} propiedad=Placement.Rotation anterior_yaw={:.3f}deg nueva_yaw={:.3f}deg modo={} resultado=OK (pitch/roll preservados)".format(
                            _object_label(obj), old_yaw, _yaw_deg(new_rot), str(rotation_mode or "abs"),
                        )
                    )
                    object_changed = True

                if object_changed:
                    changed += 1
            except Exception as obj_ex:
                skipped += 1
                log_err(
                    "[ECR][ALTURA] objeto={} resultado=ERROR razon={} accion=REVERTIR_TRANSACCION".format(
                        _object_label(obj), obj_ex,
                    )
                )
                raise

        doc.recompute()
        doc.commitTransaction()
    except Exception as ex:
        doc.abortTransaction()
        log_err("[ECR][ALTURA] Operacion cancelada: {}".format(ex))
        return False

    log_info("[ECR][ALTURA] Cambios aplicados: {} | Omitidos: {}".format(changed, skipped))
    return changed > 0


def ejecutar_dialogo():
    if QtWidgets is None:
        log_err("[ERROR] No se encontro interfaz Qt (PySide6/PySide2/PySide).")
        return
    dlg = CambiarAlturaYRotacionDialogo()
    _run_dialog(dlg)


if __name__ == "__main__":
    ejecutar_dialogo()

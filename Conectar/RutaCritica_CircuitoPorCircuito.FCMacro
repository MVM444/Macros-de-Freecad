# -*- coding: utf-8 -*-
# MenuText: Ruta critica circuito por circuito
# Icon: medir_distancia_y_dibujar_ruta.svg

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()


import os
import importlib.util
import importlib.machinery

import FreeCAD
import FreeCADGui

try:
    from PySide2 import QtWidgets as QtGui
except Exception:
    from PySide import QtGui


TAG = "[RUTA-SEQ]"
USE_RESULTS_SHEET = False


def log_info(msg):
    FreeCAD.Console.PrintMessage(f"{TAG}[INFO] {msg}\n")


def log_warn(msg):
    FreeCAD.Console.PrintWarning(f"{TAG}[WARN] {msg}\n")


def log_err(msg):
    FreeCAD.Console.PrintError(f"{TAG}[ERROR] {msg}\n")


def _selected_objects():
    sel = list(FreeCADGui.Selection.getSelection() or [])
    if sel:
        return sel
    try:
        sel_ex = FreeCADGui.Selection.getSelectionEx() or []
        return [s.Object for s in sel_ex if getattr(s, "Object", None)]
    except Exception:
        return []


def _is_group(obj):
    return hasattr(obj, "Group")


def _is_conexiones_group(obj):
    label = str(getattr(obj, "Label", "") or "").strip().lower()
    name = str(getattr(obj, "Name", "") or "").strip().lower()
    return label.startswith("conexiones") or name.startswith("conexiones")


def _direct_subgroups(grp):
    out = []
    if not hasattr(grp, "Group"):
        return out
    for child in grp.Group:
        if not _is_group(child):
            continue
        if _is_conexiones_group(child):
            continue
        out.append(child)
    return out


def _load_base_macro():
    this_dir = os.path.dirname(__file__) if "__file__" in globals() else ""
    path = os.path.join(this_dir, "medir_distancia_y_dibujar_ruta.FCMacro")
    if not os.path.isfile(path):
        raise RuntimeError(f"No se encontro macro base: {path}")

    name = "ruta_critica_base_macro"
    loader = importlib.machinery.SourceFileLoader(name, path)
    spec = importlib.util.spec_from_loader(name, loader)
    if spec is None:
        raise RuntimeError("No se pudo crear spec para macro base")
    mod = importlib.util.module_from_spec(spec)
    loader.exec_module(mod)
    return mod


def ruta_critica_circuito_por_circuito():
    doc = FreeCAD.ActiveDocument
    if doc is None:
        log_err("No hay documento activo")
        return

    sel = _selected_objects()
    if len(sel) < 2:
        log_err("Seleccione primero el objeto inicial y luego el grupo principal de circuitos")
        return

    objeto_inicial = sel[0]
    grupo_principal = sel[1]

    if not hasattr(objeto_inicial, "Placement"):
        log_err("El primer elemento seleccionado no tiene Placement")
        return
    if not _is_group(grupo_principal):
        log_err("El segundo elemento seleccionado debe ser un grupo")
        return

    circuitos = _direct_subgroups(grupo_principal)
    if not circuitos:
        if _is_conexiones_group(grupo_principal):
            log_err("Seleccione un grupo principal de circuitos, no 'Conexiones'")
            return
        circuitos = [grupo_principal]

    altura, ok = QtGui.QInputDialog.getDouble(
        None, "Altura", "Ingrese altura Z de las rutas (mm):",
        3000, -100000, 100000, 2
    )
    if not ok:
        log_warn("Operacion cancelada por el usuario")
        return

    try:
        base = _load_base_macro()
    except Exception as ex:
        log_err(f"No se pudo cargar macro base: {ex}")
        return

    runner = getattr(base, "run_ruta_critica", None)
    if runner is None:
        log_err("La macro base no expone run_ruta_critica(). Actualice medir_distancia_y_dibujar_ruta.FCMacro")
        return

    hoja = base.ensure_results_sheet(doc) if USE_RESULTS_SHEET else None
    next_row = None if USE_RESULTS_SHEET else 2
    total_wires = 0

    log_info(f"Circuitos a procesar: {len(circuitos)}")
    for idx, circuito in enumerate(circuitos, 1):
        c_label = getattr(circuito, "Label", getattr(circuito, "Name", "Circuito"))
        log_info(f"[{idx}/{len(circuitos)}] Procesando '{c_label}'")
        try:
            res = runner(
                objeto_inicial=objeto_inicial,
                grupo_tomas=circuito,
                altura=altura,
                hoja=hoja,
                base_row=next_row,
                recompute=False,
                update_e1=False,
                write_sheet=USE_RESULTS_SHEET,
            )
            wrote = int(res.get("wrote", 0))
            if USE_RESULTS_SHEET:
                next_row = res.get("next_row", next_row)
            total_wires += max(0, wrote)
            if wrote == 0:
                log_warn(f"Sin ruta creada en '{c_label}'")
        except Exception as ex:
            log_err(f"Fallo en '{c_label}': {ex}")

    if USE_RESULTS_SHEET and next_row is not None and hoja is not None:
        try:
            base.bump_e1(hoja, next_row)
        except Exception as ex:
            log_warn(f"No se pudo actualizar E1: {ex}")

    try:
        doc.recompute()
    except Exception as ex:
        log_warn(f"Error en recompute: {ex}")

    log_info(f"Listo. Rutas creadas: {total_wires}")


if __name__ == "__main__":
    ruta_critica_circuito_por_circuito()

# -*- coding: utf-8 -*-
# MenuText: Colocar Luminarias Link
# ToolTip: Colocar luminarias por rejilla usando App::Link
# Icon: ColocarLuminarias.svg
# Revision: 2026-08-10 11:40 CST - la altura elegida gobierna el modelo 3D.

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

# Transaction: self
"""
ColocarLuminarias_Link.FCMacro

Same flow as ColocarLuminarias_Objeto, but instances are App::Link.
No clones are used.
"""

from pathlib import Path
import json

import FreeCAD as App
import FreeCADGui as Gui

try:
    from PySide2 import QtWidgets
except Exception:
    from PySide import QtGui as QtWidgets


MACRO_FILE = Path(__file__).resolve()
REPO_ROOT = MACRO_FILE.parent.parent
REGISTRY_CANDIDATES = (
    REPO_ROOT / "Resources" / "registry" / "registry_electric.json",
    Path(App.getUserMacroDir()) / "Resources" / "registry" / "registry_electric.json",
)
REG_PATH = REGISTRY_CANDIDATES[0]


def _ts():
    from datetime import datetime
    return datetime.now().strftime("%Y-%m-%d %H:%M:%S")


def log_i(msg):
    App.Console.PrintMessage("[{}][LNKRECT][INFO] {}\n".format(_ts(), msg))


def log_w(msg):
    App.Console.PrintWarning("[{}][LNKRECT][WARN] {}\n".format(_ts(), msg))


def log_e(msg):
    App.Console.PrintError("[{}][LNKRECT][ERROR] {}\n".format(_ts(), msg))


def load_registry():
    for path in REGISTRY_CANDIDATES:
        try:
            data = json.loads(path.read_text(encoding="utf-8-sig"))
            types = data.get("types") if isinstance(data, dict) else None
            if isinstance(types, dict) and types:
                log_i("Registro cargado: {} ({} tipos)".format(path, len(types)))
                return data
            log_w("Registro vacío o sin 'types': {}".format(path))
        except Exception as ex:
            log_w("No se pudo leer {}: {}".format(path, ex))
    log_e("No se encontró un registro válido. Rutas revisadas: {}".format(
        " | ".join(str(path) for path in REGISTRY_CANDIDATES)
    ))
    return {"schema": "1.0.0", "types": {}}


def type_keys_sorted_for_ui(reg):
    keys = list((reg.get("types") or {}).keys())
    keys.sort(key=lambda k: (0 if "lumin" in k.lower() else 1, k.lower()))
    return keys


def ensure_electriccr_on_path():
    import importlib
    import sys

    for name in ("ElectricCR", "electriccr"):
        try:
            importlib.import_module(name)
            return True
        except Exception:
            pass

    try:
        here = Path(__file__).resolve()
        cands = []
        for parent in [here.parent] + list(here.parents):
            cand = parent / "ElectricCR"
            if cand.is_dir():
                cands.append(str(cand.parent))
                cands.append(str(cand))
        try:
            base = Path(App.getUserAppDataDir())
        except Exception:
            base = Path.home() / "AppData" / "Roaming" / "FreeCAD"
        for nm in ("Macro", "Macros"):
            cand = base / nm / "ElectricCR"
            if cand.is_dir():
                cands.append(str(cand.parent))
                cands.append(str(cand))
        for p in cands:
            if p and p not in sys.path:
                sys.path.insert(0, p)
        importlib.invalidate_caches()
        for name in ("ElectricCR", "electriccr"):
            try:
                importlib.import_module(name)
                return True
            except Exception:
                pass
    except Exception:
        pass

    log_w("No se pudo localizar el paquete ElectricCR.")
    return False


def get_crear_toma_uno():
    if not ensure_electriccr_on_path():
        return None
    try:
        from ElectricCR.electriccr.features.objeto_toma_uno import crear_toma_uno
        return crear_toma_uno
    except Exception:
        pass
    try:
        from electriccr.features.objeto_toma_uno import crear_toma_uno
        return crear_toma_uno
    except Exception as ex:
        log_e("No se pudo importar crear_toma_uno: {}".format(ex))
        return None


def collect_rectangles_from_selection():
    rects = []
    sel = Gui.Selection.getSelection() or []
    for obj in sel:
        if getattr(obj, "TypeId", "") == "App::DocumentObjectGroup":
            for child in (obj.Group or []):
                if getattr(getattr(child, "Proxy", None), "Type", "") == "Rectangle":
                    rects.append(child)
        else:
            if getattr(getattr(obj, "Proxy", None), "Type", "") == "Rectangle":
                rects.append(obj)
    return rects


def rect_dims_cols_rows(rect):
    try:
        width = float(rect.Length.Value)
        height = float(rect.Height.Value)
    except Exception:
        return None
    if not hasattr(rect, "Columns") or not hasattr(rect, "Rows"):
        return None
    try:
        cols = int(rect.Columns)
        rows = int(rect.Rows)
    except Exception:
        return None
    return width, height, cols, rows


def _sanitize_token(text, fallback="Obj"):
    raw = str(text or "").strip()
    chars = []
    for ch in raw:
        chars.append(ch if (ch.isalnum() or ch == "_") else "_")
    out = "".join(chars).strip("_")
    if not out:
        out = fallback
    if out[0].isdigit():
        out = "{}_{}".format(fallback, out)
    return out


def _unique_name(doc, base):
    token = _sanitize_token(base, "Obj")
    cand = token
    idx = 1
    while doc.getObject(cand) is not None:
        cand = "{}_{:03d}".format(token, idx)
        idx += 1
    return cand


def ensure_main_group(doc):
    grp = doc.getObject("electrico")
    if grp is None:
        grp = doc.addObject("App::DocumentObjectGroup", "electrico")
        grp.Label = "electrico"
        log_i("Grupo creado: electrico")
    return grp


def ensure_link_output_group(doc, prefix_label):
    main = ensure_main_group(doc)
    label = (str(prefix_label or "").rstrip("_") or "Luminarias") + "_Link"
    for child in getattr(main, "Group", []) or []:
        if getattr(child, "TypeId", "") == "App::DocumentObjectGroup" and getattr(child, "Label", "") == label:
            return child
    name = _unique_name(doc, label)
    grp = doc.addObject("App::DocumentObjectGroup", name)
    grp.Label = label
    main.addObject(grp)
    log_i("Subgrupo creado: {}".format(label))
    return grp


def ensure_link_library_group(doc):
    main = ensure_main_group(doc)

    glib = doc.getObject("_lib")
    if glib is None:
        glib = doc.addObject("App::DocumentObjectGroup", "_lib")
        glib.Label = "_lib"
    if glib not in (getattr(main, "Group", []) or []):
        try:
            main.addObject(glib)
        except Exception:
            pass

    target_label = "Luminarias_Link_Masters"
    for child in getattr(glib, "Group", []) or []:
        if getattr(child, "TypeId", "") == "App::DocumentObjectGroup" and getattr(child, "Label", "") == target_label:
            return child

    name = _unique_name(doc, target_label)
    grp = doc.addObject("App::DocumentObjectGroup", name)
    grp.Label = target_label
    glib.addObject(grp)
    return grp


def ensure_prop(obj, ptype, pname, pgroup, pdoc):
    if hasattr(obj, pname):
        return
    try:
        obj.addProperty(ptype, pname, pgroup, pdoc)
    except Exception:
        pass


def _near(a, b, eps=1e-6):
    try:
        return abs(float(a) - float(b)) <= float(eps)
    except Exception:
        return False


def find_existing_master(doc, key_registro, altura_rel, modo_visual):
    for obj in doc.Objects:
        tid = str(getattr(obj, "TypeId", "") or "")
        if tid == "App::Link":
            continue
        k = str(getattr(obj, "LnkMasterKey", "") or "")
        if k != str(key_registro):
            continue
        m = str(getattr(obj, "LnkMasterMode", "") or "")
        if m != str(modo_visual):
            continue
        h = getattr(obj, "LnkMasterAltura", None)
        if not _near(h, altura_rel):
            continue
        return obj
    return None


def ensure_link_master(doc, crear_toma_uno, key_registro, altura_rel, modo_visual, reuse=True):
    if reuse:
        old = find_existing_master(doc, key_registro, altura_rel, modo_visual)
        if old is not None:
            return old

    master = crear_toma_uno(
        doc,
        name_prefix="MasterLink_",
        key_registro=key_registro,
        tipo_logico="Luminaria",
    )
    if master is None:
        log_e("crear_toma_uno devolvio None para '{}'".format(key_registro))
        return None

    try:
        master.AlturaRel = float(altura_rel)
    except Exception:
        pass
    try:
        master.ModoVisual = str(modo_visual)
    except Exception:
        pass
    try:
        master.OrientacionPared = "Vertical"
    except Exception:
        pass
    try:
        master.Placement = App.Placement(App.Vector(0, 0, 0), App.Rotation())
    except Exception:
        pass

    ensure_prop(master, "App::PropertyString", "LnkMasterKey", "Link", "Key de registro del master link")
    ensure_prop(master, "App::PropertyFloat", "LnkMasterAltura", "Link", "Altura del master link")
    ensure_prop(master, "App::PropertyString", "LnkMasterMode", "Link", "Modo visual del master link")
    try:
        master.LnkMasterKey = str(key_registro)
        master.LnkMasterAltura = float(altura_rel)
        master.LnkMasterMode = str(modo_visual)
    except Exception:
        pass

    # AlturaRel changes the generated Shape, so make the FeaturePython execute
    # again on the document recompute before any App::Link is displayed.
    try:
        master.touch()
    except Exception:
        pass

    try:
        master.Label = "Master Link {} {}mm {}".format(
            str(key_registro), int(round(float(altura_rel))), str(modo_visual)
        )
    except Exception:
        pass

    glib = ensure_link_library_group(doc)
    if master not in (getattr(glib, "Group", []) or []):
        try:
            glib.addObject(master)
        except Exception:
            pass

    try:
        if hasattr(master, "ViewObject"):
            master.ViewObject.Visibility = False
            if hasattr(master.ViewObject, "Selectable"):
                master.ViewObject.Selectable = False
            if hasattr(master.ViewObject, "Pickable"):
                master.ViewObject.Pickable = False
    except Exception:
        pass

    return master


def insert_link_in_cell(doc, master, prefix, rect, rect_pos, rect_rot, x_local, y_local, idx_global, group=None):
    base = rect_pos + rect_rot.multVec(App.Vector(float(x_local), float(y_local), 0.0))
    obj_name = _unique_name(doc, "{}{:03d}".format(_sanitize_token(prefix, "Luminaria_"), idx_global))
    link = doc.addObject("App::Link", obj_name)
    if hasattr(link, "LinkedObject"):
        link.LinkedObject = master
    else:
        link.Link = master
    try:
        if hasattr(link, "LinkTransform"):
            link.LinkTransform = True
    except Exception:
        pass
    link.Placement = App.Placement(base, rect_rot)
    try:
        link.Label = "{}_{}{:03d}".format(rect.Label, str(prefix), idx_global)
    except Exception:
        pass
    try:
        vo = getattr(link, "ViewObject", None)
        if vo is not None:
            if hasattr(vo, "Selectable"):
                vo.Selectable = True
            if hasattr(vo, "Pickable"):
                vo.Pickable = True
    except Exception:
        pass
    if group is not None:
        try:
            group.addObject(link)
        except Exception:
            pass
    return link


def tag_link_ceiling_cell(link, module, row, column, room_label):
    """Store the modular-ceiling contract consumed by Facil Arquitectura."""
    ensure_prop(link, "App::PropertyLength", "ECR_CeilingModule", "ElectricCR", "Modulo del cielo")
    ensure_prop(link, "App::PropertyInteger", "ECR_CeilingRow", "ElectricCR", "Fila de celda")
    ensure_prop(link, "App::PropertyInteger", "ECR_CeilingColumn", "ElectricCR", "Columna de celda")
    ensure_prop(link, "App::PropertyString", "ECR_CeilingRoom", "ElectricCR", "Recinto del cielo")
    ensure_prop(link, "App::PropertyBool", "ECR_CeilingAligned", "ElectricCR", "Alineada al modulo")
    link.ECR_CeilingModule = float(module)
    link.ECR_CeilingRow = int(row)
    link.ECR_CeilingColumn = int(column)
    link.ECR_CeilingRoom = str(room_label)
    link.ECR_CeilingAligned = True
    return link


def ensure_group_links_selectable(group_obj):
    if group_obj is None:
        return 0
    cnt = 0
    for obj in getattr(group_obj, "Group", []) or []:
        if str(getattr(obj, "TypeId", "") or "") != "App::Link":
            continue
        try:
            vo = getattr(obj, "ViewObject", None)
            if vo is not None:
                if hasattr(vo, "Selectable"):
                    vo.Selectable = True
                if hasattr(vo, "Pickable"):
                    vo.Pickable = True
                cnt += 1
        except Exception:
            pass
    return cnt


def ensure_all_links_selectable(doc):
    if doc is None:
        return 0
    cnt = 0
    for obj in getattr(doc, "Objects", []) or []:
        if str(getattr(obj, "TypeId", "") or "") != "App::Link":
            continue
        try:
            vo = getattr(obj, "ViewObject", None)
            if vo is not None:
                if hasattr(vo, "Selectable"):
                    vo.Selectable = True
                if hasattr(vo, "Pickable"):
                    vo.Pickable = True
                cnt += 1
        except Exception:
            pass
    return cnt


def unlock_pick_chain_for_links(doc):
    if doc is None:
        return 0
    touched = 0
    visited = set()
    for obj in getattr(doc, "Objects", []) or []:
        if str(getattr(obj, "TypeId", "") or "") != "App::Link":
            continue
        stack = [obj]
        stack.extend(getattr(obj, "InList", []) or [])
        stack.extend(getattr(obj, "OutList", []) or [])
        while stack:
            cur = stack.pop()
            if cur is None:
                continue
            name = str(getattr(cur, "Name", "") or "")
            if name and name in visited:
                continue
            if name:
                visited.add(name)
            try:
                vo = getattr(cur, "ViewObject", None)
                if vo is not None:
                    changed = False
                    if hasattr(vo, "Selectable"):
                        vo.Selectable = True
                        changed = True
                    if hasattr(vo, "Pickable"):
                        vo.Pickable = True
                        changed = True
                    if changed:
                        touched += 1
            except Exception:
                pass
            for n in getattr(cur, "InList", []) or []:
                stack.append(n)
            for n in getattr(cur, "OutList", []) or []:
                stack.append(n)
    return touched


class PickTypeDialog(QtWidgets.QDialog):
    def __init__(self, reg, parent=None):
        super(PickTypeDialog, self).__init__(parent)
        self.setWindowTitle("Insertar luminarias Link en rectangulos")
        self.setMinimumWidth(440)
        self.reg = reg

        self.cmb_tipo = QtWidgets.QComboBox()
        self.cmb_tipo.addItems(type_keys_sorted_for_ui(self.reg))
        self.cmb_tipo.currentIndexChanged.connect(self._on_tipo_changed)

        self.le_prefix = QtWidgets.QLineEdit("Luminaria_")

        self.sp_altura = QtWidgets.QDoubleSpinBox()
        self.sp_altura.setRange(0.0, 10000.0)
        self.sp_altura.setDecimals(1)
        self.sp_altura.setSuffix(" mm")
        self.sp_altura.setValue(300.0)

        self.cmb_modo = QtWidgets.QComboBox()
        self.cmb_modo.addItems(["Ambos", "Solo2D", "Solo3D"])

        self.chk_reuse = QtWidgets.QCheckBox("Reusar master Link existente")
        self.chk_reuse.setChecked(True)

        self.chk_area_type = QtWidgets.QCheckBox("Usar el tipo asignado en cada area")
        self.chk_area_type.setChecked(True)

        self.chk_ceiling_module = QtWidgets.QCheckBox("Alinear a cielo modular")
        self.chk_ceiling_module.setChecked(True)
        self.sp_ceiling_module = QtWidgets.QDoubleSpinBox()
        self.sp_ceiling_module.setRange(100.0, 2400.0)
        self.sp_ceiling_module.setDecimals(1)
        self.sp_ceiling_module.setSingleStep(50.0)
        self.sp_ceiling_module.setSuffix(" mm")
        self.sp_ceiling_module.setValue(600.0)
        self.chk_ceiling_module.toggled.connect(self.sp_ceiling_module.setEnabled)

        form = QtWidgets.QFormLayout()
        form.addRow("Tipo (registro):", self.cmb_tipo)
        form.addRow("Prefijo:", self.le_prefix)
        form.addRow("Altura:", self.sp_altura)
        form.addRow("Modo visual:", self.cmb_modo)
        form.addRow("", self.chk_area_type)
        form.addRow("", self.chk_reuse)
        form.addRow("", self.chk_ceiling_module)
        form.addRow("Modulo del cielo:", self.sp_ceiling_module)

        btn_ok = QtWidgets.QPushButton("Insertar")
        btn_cancel = QtWidgets.QPushButton("Cancelar")
        btn_ok.clicked.connect(self.accept)
        btn_cancel.clicked.connect(self.reject)
        row = QtWidgets.QHBoxLayout()
        row.addStretch(1)
        row.addWidget(btn_cancel)
        row.addWidget(btn_ok)

        lay = QtWidgets.QVBoxLayout(self)
        lay.addLayout(form)
        lay.addStretch(1)
        lay.addLayout(row)

        self._apply_defaults()

    def selected_key(self):
        return str(self.cmb_tipo.currentText()).strip()

    def selected_prefix(self):
        return str(self.le_prefix.text()).strip() or "Luminaria_"

    def selected_altura(self):
        return float(self.sp_altura.value())

    def selected_mode(self):
        return str(self.cmb_modo.currentText()).strip() or "Ambos"

    def reuse_master(self):
        return bool(self.chk_reuse.isChecked())

    def use_assigned_area_type(self):
        return bool(self.chk_area_type.isChecked())

    def use_ceiling_module(self):
        return bool(self.chk_ceiling_module.isChecked())

    def ceiling_module(self):
        return float(self.sp_ceiling_module.value())

    def _apply_defaults(self):
        info = (self.reg.get("types") or {}).get(self.selected_key(), {}) or {}
        d = info.get("defaults", {}) or {}
        try:
            self.sp_altura.setValue(float(d.get("altura", 300.0)))
        except Exception:
            pass
        modo = str(d.get("modo", "Both") or "Both")
        mode_map = {
            "Both": "Ambos",
            "Ambos": "Ambos",
            "Solo2D": "Solo2D",
            "Solo 2D": "Solo2D",
            "Solo3D": "Solo3D",
            "Solo 3D": "Solo3D",
        }
        target = mode_map.get(modo, "Ambos")
        idx = self.cmb_modo.findText(target)
        if idx >= 0:
            self.cmb_modo.setCurrentIndex(idx)

    def _on_tipo_changed(self, _idx):
        self._apply_defaults()


def resolve_rectangle_luminaire_settings(
    rect, reg, selected_key, selected_height, selected_mode, use_assigned_area_type
):
    """Resolve the type per area while keeping the dialog height authoritative."""
    rect_key = (
        str(getattr(rect, "LightingTypeKey", "") or "").strip()
        if use_assigned_area_type else ""
    )
    if rect_key and rect_key not in (reg.get("types") or {}):
        log_w("{}: tipo asignado '{}' no existe; se usa '{}'.".format(
            rect.Label, rect_key, selected_key
        ))
        rect_key = ""

    active_key = rect_key or selected_key
    active_info = (reg.get("types") or {}).get(active_key, {}) or {}
    active_defaults = active_info.get("defaults", {}) or {}

    # The checkbox promises only to select the type assigned to each area.
    # LightingMountHeight and the registry default must not silently replace
    # the height that the user explicitly entered in this dialog.
    active_height = float(selected_height)

    default_mode = str(active_defaults.get("modo", selected_mode) or selected_mode)
    active_mode = {
        "Both": "Ambos",
        "Solo 2D": "Solo2D",
        "Solo 3D": "Solo3D",
    }.get(default_mode, default_mode)
    if not rect_key:
        active_mode = selected_mode
    return rect_key, active_key, active_height, active_mode


def run():
    doc = App.ActiveDocument or App.newDocument("Electrico")

    rects = collect_rectangles_from_selection()
    if not rects:
        log_e("Debe seleccionar al menos un rectangulo (o grupo con rectangulos).")
        return

    reg = load_registry()
    if not (reg.get("types") or {}):
        log_e("El registro no tiene tipos definidos.")
        return

    dlg = PickTypeDialog(reg, Gui.getMainWindow())
    if dlg.exec_() != QtWidgets.QDialog.Accepted:
        return

    key = dlg.selected_key()
    prefix = dlg.selected_prefix()
    altura_rel = dlg.selected_altura()
    modo_visual = dlg.selected_mode()
    reuse_master = dlg.reuse_master()
    use_assigned_area_type = dlg.use_assigned_area_type()
    use_ceiling_module = dlg.use_ceiling_module()
    ceiling_module = dlg.ceiling_module()

    crear_toma_uno = get_crear_toma_uno()
    if not crear_toma_uno:
        return

    modular_grid_positions = None
    if use_ceiling_module:
        try:
            from electriccr.features.ceiling_grid import modular_grid_positions
        except Exception as ex:
            log_w("No se pudo cargar la distribucion modular; se usara la rejilla proporcional: {}".format(ex))

    created = 0
    doc.openTransaction("ElectricCR: Colocar Luminarias Link")
    try:
        masters = {}
        output_groups = {}

        for rect in rects:
            rect_key, active_key, active_height, active_mode = resolve_rectangle_luminaire_settings(
                rect,
                reg,
                selected_key=key,
                selected_height=altura_rel,
                selected_mode=modo_visual,
                use_assigned_area_type=use_assigned_area_type,
            )
            master_token = (active_key, round(active_height, 3), active_mode)
            master = masters.get(master_token)
            if master is None:
                master = ensure_link_master(
                    doc, crear_toma_uno, key_registro=active_key, altura_rel=active_height,
                    modo_visual=active_mode, reuse=reuse_master,
                )
                if master is None:
                    raise RuntimeError("No se pudo crear/resolver master Link para '{}'.".format(active_key))
                masters[master_token] = master
            active_prefix = prefix if not rect_key else (_sanitize_token(active_key, "Luminaria") + "_")
            out_group = output_groups.get(active_prefix)
            if out_group is None:
                out_group = ensure_link_output_group(doc, active_prefix)
                output_groups[active_prefix] = out_group

            dims = rect_dims_cols_rows(rect)
            if not dims:
                log_w("Rectangulo '{}' sin Length/Height/Columns/Rows validos.".format(rect.Label))
                continue
            width, height, cols, rows = dims
            if cols < 1 or rows < 1:
                log_w("Rectangulo '{}' con cols/rows invalidos ({}x{}).".format(rect.Label, cols, rows))
                continue

            rect_pl = rect.Placement
            rect_pos = rect_pl.Base
            rect_rot = rect_pl.Rotation

            log_i(
                "Procesando {}: {}x{} | tipo={} | altura={:.1f} mm | W={:.1f} H={:.1f}".format(
                    rect.Label, cols, rows, active_key, active_height, width, height
                )
            )

            modular_positions = None
            if modular_grid_positions is not None:
                try:
                    modular_positions = modular_grid_positions(width, height, cols, rows, ceiling_module)
                    log_i(
                        "Alineamiento de cielo activo: modulo {:.1f} mm | {} celdas".format(
                            ceiling_module, len(modular_positions)
                        )
                    )
                except Exception as ex:
                    log_w("{}: no se pudo modular; se conserva distribucion proporcional ({})".format(rect.Label, ex))
            if modular_positions is None:
                dist_x = width / float(cols)
                dist_y = height / float(rows)
                modular_positions = [
                    {
                        "x": (c + 0.5) * dist_x,
                        "y": (r + 0.5) * dist_y,
                        "cell_row": -1,
                        "cell_column": -1,
                    }
                    for r in range(rows)
                    for c in range(cols)
                ]

            for position in modular_positions:
                    link = insert_link_in_cell(
                        doc,
                        master=master,
                        prefix=active_prefix,
                        rect=rect,
                        rect_pos=rect_pos,
                        rect_rot=rect_rot,
                        x_local=position["x"],
                        y_local=position["y"],
                        idx_global=created + 1,
                        group=out_group,
                    )
                    if int(position.get("cell_row", -1)) >= 0:
                        tag_link_ceiling_cell(
                            link,
                            ceiling_module,
                            position["cell_row"],
                            position["cell_column"],
                            rect.Label,
                        )
                    created += 1

        unlocked = sum(ensure_group_links_selectable(group) for group in output_groups.values())
        if unlocked:
            log_i("Links seleccionables asegurados: {}".format(unlocked))
        unlocked_all = ensure_all_links_selectable(doc)
        if unlocked_all:
            log_i("Links seleccionables globales: {}".format(unlocked_all))
        chain = unlock_pick_chain_for_links(doc)
        if chain:
            log_i("Cadena pick de links desbloqueada: {}".format(chain))

        doc.recompute()
        doc.commitTransaction()
    except Exception as ex:
        doc.abortTransaction()
        log_e("Insercion cancelada: {}".format(ex))
        return

    used_types = sorted(set(token[0] for token in masters)) if 'masters' in locals() else [key]
    log_i("Insercion Link finalizada. Creados: {} | Tipos: {}".format(created, ", ".join(used_types)))


if __name__ == "__main__":
    run()

#!/usr/bin/env python
# -*- coding: utf-8 -*-
# ============================================================================
# InsertarTomacorriente Fabrica (v1)
# Crea TomacorrienteHibrido (padre) con hijos Rep2D y Rep3D, propiedades
# obligatorias y ubicacion en electrico/tomacorrientes/.
# ============================================================================

import FreeCAD as App
import FreeCADGui as Gui
import Part
import os
import uuid
from math import atan2, degrees

LOG_TAG = "[TOMA23D]"

def _info(m): App.Console.PrintMessage(f"{LOG_TAG}[INFO] {m}\n")
def _warn(m): App.Console.PrintWarning(f"{LOG_TAG}[WARN] {m}\n")
def _err(m): App.Console.PrintError(f"{LOG_TAG}[ERROR] {m}\n")


# -------------------------
# Resource discovery
# -------------------------
def _resource_dirs():
    dirs = []
    try:
        here = os.path.dirname(os.path.abspath(__file__))
        dirs.append(os.path.join(here, "..", "..", "Resources"))
    except Exception:
        pass
    try:
        udir = App.getUserMacroDir()
        if udir:
            dirs.append(os.path.join(udir, "Resources"))
    except Exception:
        pass
    try:
        sep = ";" if os.name == "nt" else ":"
        mp = App.ParamGet("User parameter:BaseApp/Preferences/Macro").GetString("MacroPath", "")
        for p in mp.split(sep):
            p = p.strip()
            if p:
                dirs.append(os.path.join(p, "Resources"))
    except Exception:
        pass
    # unique
    seen = set(); out = []
    for d in dirs:
        d2 = os.path.abspath(d)
        if d2 not in seen:
            out.append(d2); seen.add(d2)
    return out

def _find_resource_files():
    for d in _resource_dirs():
        a2 = os.path.join(d, "SimboloToma.step")
        a3 = os.path.join(d, "tomacorriente-3D.step")
        if os.path.exists(a2) and os.path.exists(a3):
            return a2, a3
    return None, None


# -------------------------
# Group helpers
# -------------------------
def _ensure_group_path(doc, path_elems):
    parent = None
    current = None
    for name in path_elems:
        # search existing under parent
        found = None
        cand = doc.Objects if parent is None else getattr(parent, 'Group', [])
        for obj in cand:
            if obj.Label == name and obj.TypeId in ("App::DocumentObjectGroup", "App::Part"):
                found = obj
                break
        if not found:
            # prefer DocumentObjectGroup
            found = doc.addObject("App::DocumentObjectGroup", name)
            if parent is not None:
                try:
                    parent.addObject(found)
                except Exception:
                    g = list(getattr(parent, 'Group', [])); g.append(found); parent.Group = g
        parent = found
        current = found
    return current


# -------------------------
# Library prototypes (shared)
# -------------------------
def _ensure_library(doc):
    return _ensure_group_path(doc, ["electrico", "_lib"])

def _get_or_create_prototypes(doc):
    lib = _ensure_library(doc)
    # search existing
    proto2d = None
    proto3d = None
    for o in getattr(lib, 'Group', []):
        if o.Label == 'ProtoToma2D':
            proto2d = o
        elif o.Label == 'ProtoToma3D':
            proto3d = o
    a2, a3 = _find_resource_files()
    if proto2d is None:
        if a2:
            proto2d = _make_child_from_step(doc, 'ProtoToma2D', a2)
        else:
            proto2d = _make_placeholder_2d(doc, 'ProtoToma2D')
        try:
            lib.addObject(proto2d)
        except Exception:
            lib.Group = list(getattr(lib, 'Group', [])) + [proto2d]
        try:
            proto2d.ViewObject.Visibility = False
            proto2d.ViewObject.ShowInTree = False
        except Exception:
            pass
    if proto3d is None:
        if a3:
            proto3d = _make_child_from_step(doc, 'ProtoToma3D', a3)
        else:
            proto3d = _make_placeholder_3d(doc, 'ProtoToma3D')
        try:
            lib.addObject(proto3d)
        except Exception:
            lib.Group = list(getattr(lib, 'Group', [])) + [proto3d]
        try:
            proto3d.ViewObject.Visibility = False
            proto3d.ViewObject.ShowInTree = False
        except Exception:
            pass
    return proto2d, proto3d


# -------------------------
# Parent helpers (no proxy, works with App::Part)
# -------------------------
def _setup_parent(parent):
    grp = "Tomacorriente"
    parent.addProperty("App::PropertyString", "Categoria", grp, "Fixed category").Categoria = "Tomacorriente"
    parent.addProperty("App::PropertyString", "Tipo", grp, "Type code").Tipo = "NEMA5-15_duplex"
    parent.addProperty("App::PropertyString", "EtiquetaPlano", grp, "Plan label").EtiquetaPlano = "Toma"
    parent.addProperty("App::PropertyString", "UUID", grp, "Unique id").UUID = str(uuid.uuid4())
    parent.addProperty("App::PropertyString", "SchemaVersion", grp, "Schema version").SchemaVersion = "2025-09-15T14:00Z"
    parent.addProperty("App::PropertyEnumeration", "ModoVisual", grp, "2D/3D visibility").ModoVisual = ["Ambos","Solo2D","Solo3D"]
    parent.ModoVisual = "Ambos"
    parent.addProperty("App::PropertyLength", "Altura", grp, "Height Z").Altura = 300
    parent.addProperty("App::PropertyAngle", "Giro", grp, "Yaw deg").Giro = 0.0
    parent.addProperty("App::PropertyLength", "OffsetX", grp, "Local X").OffsetX = 0
    parent.addProperty("App::PropertyLength", "OffsetY", grp, "Local Y").OffsetY = 0
    parent.addProperty("App::PropertyString", "CircuitoID", grp, "Circuit id").CircuitoID = ""
    parent.addProperty("App::PropertyString", "Rep2DName", grp, "child 2d name").Rep2DName = "Rep2D"
    parent.addProperty("App::PropertyString", "Rep3DName", grp, "child 3d name").Rep3DName = "Rep3D"

def _children(parent):
    return list(getattr(parent, 'Group', []))

def _child_by_label(parent, label):
    for ch in _children(parent):
        if ch.Label == label:
            return ch
    return None

def _update_visibility(parent):
    mode = str(getattr(parent, 'ModoVisual', 'Ambos'))
    rep2d = _child_by_label(parent, getattr(parent, 'Rep2DName', 'Rep2D'))
    rep3d = _child_by_label(parent, getattr(parent, 'Rep3DName', 'Rep3D'))
    try:
        if rep2d: rep2d.ViewObject.Visibility = (mode in ("Ambos","Solo2D"))
        if rep3d: rep3d.ViewObject.Visibility = (mode in ("Ambos","Solo3D"))
    except Exception:
        pass

def _apply_transform(parent):
    offx = getattr(getattr(parent, 'OffsetX', 0), 'Value', getattr(parent, 'OffsetX', 0))
    offy = getattr(getattr(parent, 'OffsetY', 0), 'Value', getattr(parent, 'OffsetY', 0))
    alt  = getattr(getattr(parent, 'Altura', 0), 'Value', getattr(parent, 'Altura', 0))
    yaw  = float(getattr(parent, 'Giro', 0.0))
    try:
        pl = parent.Placement
        # XY offsets and yaw on parent; Z altitude is applied to Rep3D only
        base = pl.Base
        pl.Base = App.Vector((offx or 0) + base.x*0 + 0, (offy or 0) + base.y*0 + 0, base.z)
        pl.Rotation = App.Rotation(App.Vector(0,0,1), yaw)
        parent.Placement = pl
    except Exception as e:
        _warn(f"apply_transform issue: {e}")

    # set Rep3D local Z = Altura
    try:
        rep3d = _child_by_label(parent, getattr(parent, 'Rep3DName', 'Rep3D'))
        if rep3d:
            pl3 = rep3d.Placement
            pl3.Base = App.Vector(pl3.Base.x, pl3.Base.y, alt or 0)
            rep3d.Placement = pl3
    except Exception:
        pass


# -------------------------
# Placeholders
# -------------------------
def _make_placeholder_2d(doc, label):
    # simple rectangle wire in XY
    p = [App.Vector(-10,-6,0), App.Vector(10,-6,0), App.Vector(10,6,0), App.Vector(-10,6,0), App.Vector(-10,-6,0)]
    wire = Part.makePolygon(p)
    obj = doc.addObject("Part::Feature", label)
    obj.Shape = wire
    return obj

def _make_placeholder_3d(doc, label):
    # simple box
    shape = Part.makeBox(40, 25, 20)
    obj = doc.addObject("Part::Feature", label)
    obj.Shape = shape
    return obj


# -------------------------
# Create child from resource
# -------------------------
def _make_child_from_step(doc, label, path):
    try:
        sh = Part.Shape(); sh.read(path)
        obj = doc.addObject("Part::Feature", label)
        obj.Shape = sh
        return obj
    except Exception as e:
        _warn(f"STEP read failed for {label}: {e}")
        return None


# -------------------------
# Selection attach helper
# -------------------------
def _attach_by_selection(parent):
    try:
        if not App.GuiUp:
            return
        sel = Gui.Selection.getSelectionEx()
        if not sel:
            return
        s = sel[0]
        if not s.HasSubObjects or not s.SubElementNames:
            return
        # compute placement on XY workplane (2D) and yaw from edge if any
        sub = s.SubObjects[0]
        pl = parent.Placement
        # base XY from selection center, Z=0 to keep 2D on workplane
        try:
            if hasattr(sub, 'CenterOfMass'):
                c = sub.CenterOfMass
            else:
                c = sub.valueAt(0.5)
        except Exception:
            c = App.Vector(0,0,0)
        base_xy = App.Vector(c.x, c.y, 0)
        pl.Base = base_xy
        # yaw
        ang = None
        try:
            par = 0.5
            if hasattr(sub, 'FirstParameter') and hasattr(sub, 'LastParameter'):
                par = 0.5*(sub.FirstParameter+sub.LastParameter)
            tan = sub.tangentAt(par)
            tan2d = App.Vector(tan.x, tan.y, 0)
            if tan2d.Length > 0:
                ang = degrees(atan2(tan2d.y, tan2d.x))
        except Exception:
            pass
        if ang is not None:
            pl.Rotation = App.Rotation(App.Vector(0,0,1), ang)
        parent.Placement = pl
    except Exception as e:
        _err(f"_attach_by_selection error: {e}")


# -------------------------
# Factory API
# -------------------------
def InsertarTomacorriente(params=None):
    """
    params keys: Tipo (req), Altura, Giro, OffsetX, OffsetY, ModoVisual, CircuitoID
    returns parent object
    """
    doc = App.ActiveDocument or App.newDocument("PlanoElectricos")

    p = params or {}
    tipo = p.get('Tipo', 'NEMA5-15_duplex')
    altura = p.get('Altura', 300)
    giro = p.get('Giro', 0.0)
    offx = p.get('OffsetX', 0)
    offy = p.get('OffsetY', 0)
    modo = p.get('ModoVisual', 'Ambos')
    circuito = p.get('CircuitoID', '')
    etiqueta = p.get('EtiquetaPlano', 'Toma')

    # ensure group path
    grp = _ensure_group_path(doc, ["electrico", "tomacorrientes"])

    # auto numbering for label "Toma <Tipo> <nn>"
    base_label = f"Toma {tipo}"
    nn = 1
    try:
        existing = {o.Label for o in getattr(grp, 'Group', [])}
        while f"{base_label} {nn:02d}" in existing:
            nn += 1
    except Exception:
        pass

    # create parent as App::Part so children nest in tree and placement propagates
    parent = doc.addObject("App::Part", f"{base_label} {nn:02d}")
    _setup_parent(parent)

    # assign semantic properties
    parent.Tipo = str(tipo)
    parent.EtiquetaPlano = str(etiqueta)
    parent.CircuitoID = str(circuito)
    parent.ModoVisual = str(modo)
    try:
        parent.Altura = altura
        parent.Giro = giro
        parent.OffsetX = offx
        parent.OffsetY = offy
    except Exception:
        pass

    # make children as App::Link to shared prototypes
    proto2d, proto3d = _get_or_create_prototypes(doc)
    # child names fixed as Toma2D/Toma3D
    parent.Rep2DName = 'Toma2D'
    parent.Rep3DName = 'Toma3D'
    rep2d = doc.addObject('App::Link', parent.Rep2DName)
    rep2d.LinkedObject = proto2d
    rep3d = doc.addObject('App::Link', parent.Rep3DName)
    rep3d.LinkedObject = proto3d
    # reduce tree noise
    try:
        rep2d.ViewObject.ShowInTree = False
        rep3d.ViewObject.ShowInTree = False
    except Exception:
        pass

    # group children under parent
    try:
        parent.addObject(rep2d)
        parent.addObject(rep3d)
    except Exception:
        g = list(getattr(parent, 'Group', []))
        g.extend([rep2d, rep3d])
        parent.Group = g

    # ensure visibility initial state
    try:
        parent.ViewObject.Visibility = True
        rep2d.ViewObject.Visibility = True
        rep3d.ViewObject.Visibility = True
    except Exception:
        pass

    # initial placement
    _attach_by_selection(parent)
    _apply_transform(parent)
    _update_visibility(parent)

    # add to electrico/tomacorrientes group
    try:
        grp.addObject(parent)
    except Exception:
        g2 = list(getattr(grp, 'Group', [])); g2.append(parent); grp.Group = g2

    doc.recompute()
    _info(f"Inserted {parent.Label} uuid={parent.UUID}")
    return parent


# -------------------------
# Auto-run demo if executed directly
# -------------------------
def HacerEditableLocal():
    """Convert selected Toma2D/Toma3D link into a local editable copy in its parent."""
    doc = App.ActiveDocument
    if not (App.GuiUp and doc and Gui.Selection.getSelection()):
        _warn('No selection')
        return
    sel = Gui.Selection.getSelection()[0]
    # climb to parent App::Part
    parent = None
    try:
        for p in sel.InList:
            if p.TypeId == 'App::Part' and getattr(p, 'Categoria', '') == 'Tomacorriente':
                parent = p; break
    except Exception:
        pass
    if parent is None:
        _warn('Selection is not a child of Tomacorriente')
        return
    if sel.TypeId != 'App::Link' or sel.LinkedObject is None:
        _warn('Selection is not an App::Link')
        return
    # make local copy of the linked shape
    src = sel.LinkedObject
    try:
        newobj = doc.addObject('Part::Feature', sel.Label)
        newobj.Shape = getattr(src, 'Shape', None)
        # replace in parent group
        grp = list(getattr(parent, 'Group', []))
        for i, ch in enumerate(grp):
            if ch == sel:
                grp[i] = newobj
                break
        parent.Group = grp
        # remove old link
        doc.removeObject(sel.Name)
        _info('Link converted to local editable copy')
    except Exception as e:
        _err(f'Editable conversion failed: {e}')


if __name__ == '__main__':
    InsertarTomacorriente({"Tipo":"NEMA5-15_duplex"})

#!/usr/bin/env python
# -*- coding: utf-8 -*-
"""
Electric_Principal.FCMacro (MVP corregido)
Define ObjetoElectromecanico como clase genérica.
Corrige definición de enumeraciones (ModoVisual, MontajePared).
"""

import FreeCAD as App
import FreeCADGui as Gui
import Part
import os
import uuid

LOG_TAG = "[ELEC]"
SCHEMA_VERSION = "2025-09-17"
PROTO_GROUP_PATH = ["electrico", "_lib"]


def _info(msg):
    App.Console.PrintMessage(f"{LOG_TAG}[INFO] {msg}\n")


# --- utilidades ---

def _ensure_group_path(doc, names):
    parent = None
    current = None
    for label in names:
        found = None
        pool = doc.Objects if parent is None else getattr(parent, "Group", [])
        for obj in pool:
            if obj.Label == label and obj.TypeId in ("App::DocumentObjectGroup", "App::Part"):
                found = obj
                break
        if found is None:
            found = doc.addObject("App::DocumentObjectGroup", label)
            try:
                found.ViewObject.ShowInTree = False
            except Exception:
                pass
            if parent is not None:
                g = list(getattr(parent, "Group", []))
                g.append(found)
                parent.Group = g
        parent = found
        current = found
    return current


def _ensure_library(doc):
    return _ensure_group_path(doc, PROTO_GROUP_PATH)


# --- clase principal ---

class ObjetoElectromecanicoProxy:
    def __init__(self, obj):
        self.Object = obj
        self._link2d = None
        self._link3d = None
        self._ensure_properties(obj)
        obj.Proxy = self

    def _ensure_properties(self, obj):
        grp = "ObjetoElectromecanico"
        if "Placement" not in obj.PropertiesList:
            obj.addProperty("App::PropertyPlacement", "Placement", "Base", "Placement base")
        if "Tipo" not in obj.PropertiesList:
            obj.addProperty("App::PropertyString", "Tipo", grp, "Tipo de objeto")
            obj.Tipo = "Generico"
        if "ModoVisual" not in obj.PropertiesList:
            obj.addProperty("App::PropertyEnumeration", "ModoVisual", grp, "Control de visibilidad")
            obj.ModoVisual = ["Ambos", "Solo2D", "Solo3D"]
            obj.ModoVisual = "Ambos"
        if "AlturaRel" not in obj.PropertiesList:
            obj.addProperty("App::PropertyLength", "AlturaRel", grp, "Altura relativa")
            obj.AlturaRel = 0
        if "MontajePared" not in obj.PropertiesList:
            obj.addProperty("App::PropertyEnumeration", "MontajePared", grp, "Montaje en pared")
            obj.MontajePared = ["Sobrepuesto", "Empotrado"]
            obj.MontajePared = "Sobrepuesto"
        if "UUID" not in obj.PropertiesList:
            obj.addProperty("App::PropertyString", "UUID", grp, "Identificador unico")
            obj.UUID = str(uuid.uuid4())
        if "SchemaVersion" not in obj.PropertiesList:
            obj.addProperty("App::PropertyString", "SchemaVersion", grp, "Version interna")
            obj.SchemaVersion = SCHEMA_VERSION

    def execute(self, obj):
        # Actualizar hijos 2D/3D segun ModoVisual
        if self._link2d:
            self._link2d.ViewObject.Visibility = obj.ModoVisual in ("Ambos", "Solo2D")
        if self._link3d:
            self._link3d.ViewObject.Visibility = obj.ModoVisual in ("Ambos", "Solo3D")


# --- fabrica generica ---

def create_objeto_electromecanico(params=None):
    doc = App.ActiveDocument or App.newDocument("ProyectoElectrico")
    params = params or {}

    group = _ensure_group_path(doc, ["electrico", "instancias"])
    label = params.get("Label", "ObjetoElectromecanico")

    obj = doc.addObject("App::FeaturePython", label)
    try:
        obj.addExtension("App::GroupExtensionPython")
    except Exception:
        pass

    proxy = ObjetoElectromecanicoProxy(obj)

    for key, value in params.items():
        if hasattr(obj, key):
            setattr(obj, key, value)

    try:
        group.addObject(obj)
    except Exception:
        g = list(getattr(group, "Group", []))
        g.append(obj)
        group.Group = g

    doc.recompute()
    _info(f"ObjetoElectromecanico creado: {obj.Label}")
    return obj


if __name__ == "__main__":
    create_objeto_electromecanico()

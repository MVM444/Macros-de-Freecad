# -*- coding: utf-8 -*-
# MenuText: Exportar DXF/DWG (plano de trabajo)
# Icon: Exportar_DXF_DWG_Plano_Trabajo.svg

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

"""
Macro: Exportar_DXF_DWG_Plano_Trabajo
Descripcion:
- Exporta SOLO la seleccion actual.
- Opcionalmente incluye etiquetas de iluminacion.
- Filtra objetos que esten en el plano de trabajo (Draft Working Plane).
- Excluye modelos 3D (objetos fuera del plano).
- Escala mm -> m (factor 0.001) antes de exportar.
"""

import math
import os
import re
import FreeCAD as App
import FreeCADGui as Gui
import Part

try:
    from PySide2 import QtWidgets
except Exception:
    try:
        from PySide import QtGui as QtWidgets
    except Exception:
        QtWidgets = None

# ----------------------------
# Configuracion rapida
# ----------------------------
SCALE_FACTOR = 0.001  # mm -> m
PLANE_TOL_MM = 0.01   # tolerancia en mm para considerar "en el plano"
FALLBACK_Z0 = True    # si no hay Draft Working Plane, usar plano XY (Z=0)
LIGHT_LABEL_GROUP = "Etiquetas"
DEBUG_EXPORT = True
TEXT_AS_DXF_TEXT = True
TEXT_AS_OUTLINES = False
TEXT_DXF_LAYER = "0"
TEXT_DXF_WIDTH_FACTOR = 1.0
TEXT_OUTLINE_FONT = r"C:\Windows\Fonts\arial.ttf"
TEXT_DEFAULT_SIZE_MM = 200.0
TEXT_LINE_SPACING = 1.35

# ----------------------------
# Logging
# ----------------------------

def _log(msg):
    App.Console.PrintMessage(f"[DXF][INFO] {msg}\n")


def _warn(msg):
    App.Console.PrintWarning(f"[DXF][WARN] {msg}\n")


def _err(msg):
    App.Console.PrintError(f"[DXF][ERROR] {msg}\n")


def _debug(msg):
    if DEBUG_EXPORT:
        App.Console.PrintMessage(f"[DXF][DEBUG] {msg}\n")


# ----------------------------
# Plano de trabajo
# ----------------------------

def _get_workplane():
    last_err = None
    # 1) Draft.getWorkingPlane (si existe)
    try:
        import Draft
        if hasattr(Draft, "getWorkingPlane"):
            return Draft.getWorkingPlane()
        # Algunas versiones exponen Draft.WorkingPlane (modulo)
        if hasattr(Draft, "WorkingPlane"):
            wpmod = Draft.WorkingPlane
            if hasattr(wpmod, "getWorkingPlane"):
                return wpmod.getWorkingPlane()
            if hasattr(wpmod, "plane"):
                return wpmod.plane
            if hasattr(wpmod, "workingPlane"):
                return wpmod.workingPlane
    except Exception as exc:
        last_err = exc

    # 2) DraftWorkingPlane (modulo)
    try:
        import DraftWorkingPlane as DWP
        if hasattr(DWP, "getWorkingPlane"):
            return DWP.getWorkingPlane()
        if hasattr(DWP, "plane"):
            return DWP.plane
        if hasattr(DWP, "workingPlane"):
            return DWP.workingPlane
    except Exception as exc:
        last_err = exc

    # 3) DraftGui (si existe)
    try:
        import DraftGui
        if hasattr(DraftGui, "getWorkingPlane"):
            return DraftGui.getWorkingPlane()
        if hasattr(DraftGui, "workingPlane"):
            return DraftGui.workingPlane
    except Exception as exc:
        last_err = exc

    # 4) Snapper (Draft GUI)
    try:
        if hasattr(Gui, "Snapper"):
            snapper = Gui.Snapper
            if hasattr(snapper, "getWorkingPlane"):
                return snapper.getWorkingPlane()
            if hasattr(snapper, "workingPlane"):
                return snapper.workingPlane
    except Exception as exc:
        last_err = exc

    # 5) ActiveView (algunas versiones guardan el WP aqui)
    try:
        if Gui.ActiveDocument and hasattr(Gui.ActiveDocument, "ActiveView"):
            view = Gui.ActiveDocument.ActiveView
            if hasattr(view, "getActiveObject"):
                wp = view.getActiveObject("DraftWorkingPlane")
                if wp:
                    return wp
    except Exception as exc:
        last_err = exc

    return None


def _plane_origin_normal(wp):
    if wp is None:
        return App.Vector(0, 0, 0), App.Vector(0, 0, 1)

    origin = None
    for attr in ("origin", "position"):
        if hasattr(wp, attr):
            origin = getattr(wp, attr)
            break
    if origin is None:
        origin = App.Vector(0, 0, 0)

    normal = None
    for attr in ("axis", "normal"):
        if hasattr(wp, attr):
            normal = getattr(wp, attr)
            break
    if normal is None and hasattr(wp, "getNormal"):
        try:
            normal = wp.getNormal()
        except Exception:
            normal = None

    if normal is None:
        normal = App.Vector(0, 0, 1)

    try:
        if normal.Length == 0:
            normal = App.Vector(0, 0, 1)
        else:
            normal = App.Vector(normal)  # copia
            normal.normalize()
    except Exception:
        normal = App.Vector(0, 0, 1)

    return origin, normal


# ----------------------------
# Seleccion y filtros
# ----------------------------

def _flatten_selection(objs):
    out = []
    seen = set()

    def add(obj):
        if obj is None:
            return
        key = getattr(obj, "Name", None) or id(obj)
        if key in seen:
            return
        seen.add(key)
        out.append(obj)
        if hasattr(obj, "Group"):
            try:
                for child in obj.Group:
                    add(child)
            except Exception:
                pass

    for o in objs:
        add(o)
    return out


def _is_group(obj):
    try:
        return "Group" in getattr(obj, "PropertiesList", []) or hasattr(obj, "Group")
    except Exception:
        return hasattr(obj, "Group")


def _safe_text(value):
    try:
        return str(value or "")
    except Exception:
        return ""


def _norm_text(value):
    return _safe_text(value).strip().lower()


def _object_key(obj):
    return getattr(obj, "Name", None) or str(id(obj))


def _is_text_object(obj):
    type_id = _safe_text(getattr(obj, "TypeId", ""))
    if "Annotation" in type_id or "Draft::Text" in type_id:
        return True
    try:
        props = getattr(obj, "PropertiesList", []) or []
    except Exception:
        props = []
    if "Text" in props:
        return True
    proxy_name = _safe_text(getattr(getattr(obj, "Proxy", None), "__class__", ""))
    return "Text" in proxy_name or "Draft" in proxy_name and "text" in _norm_text(getattr(obj, "Label", ""))


def _debug_obj(obj):
    try:
        props = ",".join(list(getattr(obj, "PropertiesList", []) or [])[:12])
    except Exception:
        props = "?"
    try:
        groups = " / ".join(
            _safe_text(getattr(g, "Label", "")) or _safe_text(getattr(g, "Name", ""))
            for g in reversed(_parent_groups(obj))
        )
    except Exception:
        groups = ""
    return "Name={} Label={} TypeId={} Text={} Shape={} Groups=[{}] Props=[{}]".format(
        _safe_text(getattr(obj, "Name", "")),
        _safe_text(getattr(obj, "Label", "")),
        _safe_text(getattr(obj, "TypeId", "")),
        int(_is_text_object(obj)),
        int(hasattr(obj, "Shape")),
        groups,
        props,
    )


def _text_on_plane(obj, origin, normal, tol_mm):
    try:
        base = obj.Placement.Base
        return abs(normal.dot(base.sub(origin))) <= tol_mm
    except Exception:
        return True


def _parent_groups(obj):
    groups = []
    pending = list(getattr(obj, "InList", []) or [])
    seen = set()
    while pending:
        parent = pending.pop(0)
        key = _object_key(parent)
        if key in seen:
            continue
        seen.add(key)
        if _is_group(parent):
            groups.append(parent)
            pending.extend(list(getattr(parent, "InList", []) or []))
    return groups


def _is_lighting_label(obj):
    if not _is_text_object(obj):
        return False
    label = _norm_text(getattr(obj, "Label", ""))
    if not label.startswith("etiqueta_"):
        return False
    for group in _parent_groups(obj):
        group_label = _norm_text(getattr(group, "Label", ""))
        group_name = _norm_text(getattr(group, "Name", ""))
        if group_label == _norm_text(LIGHT_LABEL_GROUP) or group_name == _norm_text(LIGHT_LABEL_GROUP):
            return True
    return False


def _find_lighting_labels(doc, origin, normal, tol_mm):
    labels = []
    seen = set()
    text_candidates = 0
    for obj in getattr(doc, "Objects", []) or []:
        if _is_text_object(obj):
            text_candidates += 1
        if not _is_lighting_label(obj):
            continue
        if not _text_on_plane(obj, origin, normal, tol_mm):
            _debug("Etiqueta fuera de plano: {}".format(_debug_obj(obj)))
            continue
        key = _object_key(obj)
        if key in seen:
            continue
        seen.add(key)
        labels.append(obj)
    _debug("Textos candidatos en documento={} | etiquetas iluminacion={}".format(text_candidates, len(labels)))
    for obj in labels[:12]:
        _debug("Etiqueta detectada: {}".format(_debug_obj(obj)))
    if len(labels) > 12:
        _debug("Etiquetas adicionales no listadas: {}".format(len(labels) - 12))
    return labels


def _shape_on_plane(shape, origin, normal, tol_mm):
    if shape is None or shape.isNull():
        return False
    try:
        verts = shape.Vertexes
    except Exception:
        return False
    if not verts:
        return False
    try:
        max_abs = 0.0
        for v in verts:
            p = v.Point
            dist = normal.dot(p.sub(origin))
            ad = abs(dist)
            if ad > max_abs:
                max_abs = ad
        return max_abs <= tol_mm
    except Exception:
        return False


def _make_compound(shapes):
    try:
        return Part.Compound(shapes)
    except Exception:
        try:
            return Part.makeCompound(shapes)
        except Exception:
            return None


def _extract_planar_shape(shape, origin, normal, tol_mm):
    if shape is None or shape.isNull():
        return None

    # Si todo el shape esta en el plano, devolverlo tal cual
    if _shape_on_plane(shape, origin, normal, tol_mm):
        try:
            return shape.copy()
        except Exception:
            return shape

    # Preferir caras (si existen)
    try:
        faces = [f for f in shape.Faces if _shape_on_plane(f, origin, normal, tol_mm)]
    except Exception:
        faces = []
    if faces:
        return _make_compound(faces)

    # Luego wires
    try:
        wires = [w for w in shape.Wires if _shape_on_plane(w, origin, normal, tol_mm)]
    except Exception:
        wires = []
    if wires:
        return _make_compound(wires)

    # Finalmente edges
    try:
        edges = [e for e in shape.Edges if _shape_on_plane(e, origin, normal, tol_mm)]
    except Exception:
        edges = []
    if edges:
        return _make_compound(edges)

    return None


def _collect_planar_exportables(objs, origin, normal, tol_mm):
    shapes = []
    text_objs = []
    seen_text = set()
    debug_checked = 0

    for obj in objs:
        if DEBUG_EXPORT and debug_checked < 20:
            _debug("Seleccion revisada: {}".format(_debug_obj(obj)))
            debug_checked += 1
        if _is_text_object(obj):
            if _text_on_plane(obj, origin, normal, tol_mm):
                key = _object_key(obj)
                if key not in seen_text:
                    seen_text.add(key)
                    text_objs.append(obj)
            else:
                _debug("Texto seleccionado fuera de plano: {}".format(_debug_obj(obj)))
            continue

        try:
            shape = obj.Shape
        except Exception:
            continue
        if shape is None or shape.isNull():
            continue
        planar = _extract_planar_shape(shape, origin, normal, tol_mm)
        if planar is not None and not planar.isNull():
            shapes.append(planar)

    _debug("Seleccion exportable: geometria_2d={} textos={}".format(len(shapes), len(text_objs)))
    return shapes, text_objs


# ----------------------------
# Escala y export
# ----------------------------

def _scale_shape(shape, factor):
    try:
        s = shape.copy()
    except Exception:
        s = shape
    try:
        s.scale(factor)
        return s
    except Exception:
        try:
            m = App.Matrix()
            m.scale(factor, factor, factor)
            return s.transformGeometry(m)
        except Exception:
            return None


def _dialog_exec(dialog):
    if hasattr(dialog, "exec"):
        return dialog.exec()
    return dialog.exec_()


def _show_export_options_dialog(selected_count, lighting_label_count):
    if QtWidgets is None:
        return {
            "selection": selected_count > 0,
            "lighting_labels": lighting_label_count > 0,
        }

    dlg = QtWidgets.QDialog()
    dlg.setWindowTitle("Exportar DXF/DWG")
    layout = QtWidgets.QVBoxLayout(dlg)

    info = QtWidgets.QLabel("Seleccione que desea exportar.")
    layout.addWidget(info)

    chk_selection = QtWidgets.QCheckBox("Seleccion actual ({} elemento(s) 2D)".format(selected_count))
    chk_selection.setEnabled(selected_count > 0)
    chk_selection.setChecked(selected_count > 0)
    layout.addWidget(chk_selection)

    chk_lighting = QtWidgets.QCheckBox("Etiquetas de iluminacion ({} texto(s))".format(lighting_label_count))
    chk_lighting.setEnabled(lighting_label_count > 0)
    chk_lighting.setChecked(lighting_label_count > 0)
    layout.addWidget(chk_lighting)

    buttons = QtWidgets.QDialogButtonBox(
        QtWidgets.QDialogButtonBox.Ok | QtWidgets.QDialogButtonBox.Cancel
    )
    buttons.accepted.connect(dlg.accept)
    buttons.rejected.connect(dlg.reject)
    layout.addWidget(buttons)

    if _dialog_exec(dlg) != QtWidgets.QDialog.Accepted:
        return None

    return {
        "selection": bool(chk_selection.isChecked()),
        "lighting_labels": bool(chk_lighting.isChecked()),
    }


def _pick_output_path(doc):
    if QtWidgets is None:
        _err("Qt no disponible para dialogo de guardado.")
        return None

    base_dir = ""
    try:
        if doc and doc.FileName:
            base_dir = os.path.dirname(doc.FileName)
    except Exception:
        base_dir = ""
    if not base_dir:
        try:
            base_dir = App.getUserHomePath()
        except Exception:
            base_dir = ""

    filters = "DXF (*.dxf);;DWG (*.dwg)"
    path, selected = QtWidgets.QFileDialog.getSaveFileName(
        None,
        "Exportar DXF/DWG",
        base_dir,
        filters,
    )
    if not path:
        return None

    root, ext = os.path.splitext(path)
    if not ext:
        if "DWG" in (selected or ""):
            ext = ".dwg"
        else:
            ext = ".dxf"
        path = root + ext
    return path


def _try_importgui_export(objs, filepath):
    try:
        import ImportGui
    except Exception as exc:
        _err(f"No se pudo cargar ImportGui (exportador): {exc}")
        return False
    try:
        ImportGui.export(objs, filepath)
        return True
    except Exception as exc:
        _err(f"ImportGui.export fallo: {exc}")
        return False


def _try_dxf_export(objs, filepath):
    try:
        import importDXF
    except Exception as exc:
        _err(f"No se pudo cargar importDXF: {exc}")
        return False
    try:
        importDXF.export(objs, filepath)
        return True
    except Exception as exc:
        _err(f"importDXF.export fallo: {exc}")
        return False


def _fmt_dxf_num(value):
    try:
        text = "{:.9f}".format(float(value))
    except Exception:
        return "0"
    return text.rstrip("0").rstrip(".") or "0"


def _dxf_clean_text(value):
    text = _safe_text(value).replace("\r", " ").replace("\n", " ").replace("\t", " ")
    text = " ".join(text.split())
    return text[:250]


def _text_rotation_deg(obj):
    try:
        v = obj.Placement.Rotation.multVec(App.Vector(1, 0, 0))
        return math.degrees(math.atan2(v.y, v.x))
    except Exception:
        return 0.0


def _dxf_text_entities(text_objs, scale_factor):
    lines = []
    count = 0
    for obj in text_objs:
        try:
            placement = obj.Placement
            base = _scaled_vector(placement.Base, scale_factor)
            rot = placement.Rotation
        except Exception:
            base = App.Vector(0, 0, 0)
            rot = App.Rotation()

        height = max(_text_font_size_mm(obj) * scale_factor, 0.001)
        line_height = height * float(TEXT_LINE_SPACING)
        angle = _text_rotation_deg(obj)

        for idx, raw_line in enumerate(_text_lines(obj)):
            text = _dxf_clean_text(raw_line)
            if not text:
                continue
            try:
                offset = rot.multVec(App.Vector(0, -idx * line_height, 0))
            except Exception:
                offset = App.Vector(0, -idx * line_height, 0)
            p = base.add(offset)
            handle = "E{:05X}".format(0x10000 + count)
            lines.extend(
                [
                    "0", "TEXT",
                    "5", handle,
                    "100", "AcDbEntity",
                    "8", TEXT_DXF_LAYER,
                    "62", "7",
                    "100", "AcDbText",
                    "10", _fmt_dxf_num(p.x),
                    "20", _fmt_dxf_num(p.y),
                    "30", _fmt_dxf_num(p.z),
                    "40", _fmt_dxf_num(height),
                    "1", text,
                    "50", _fmt_dxf_num(angle),
                    "41", _fmt_dxf_num(TEXT_DXF_WIDTH_FACTOR),
                    "7", "STANDARD",
                    "100", "AcDbText",
                    "72", "0",
                    "11", _fmt_dxf_num(p.x),
                    "21", _fmt_dxf_num(p.y),
                    "31", _fmt_dxf_num(p.z),
                    "73", "0",
                ]
            )
            count += 1
    return lines, count


def _minimal_dxf_lines():
    return [
        "0", "SECTION",
        "2", "HEADER",
        "9", "$ACADVER",
        "1", "AC1009",
        "0", "ENDSEC",
        "0", "SECTION",
        "2", "TABLES",
        "0", "ENDSEC",
        "0", "SECTION",
        "2", "ENTITIES",
        "0", "ENDSEC",
        "0", "EOF",
    ]


def _find_entities_end_index(lines):
    start = None
    for i in range(0, max(len(lines) - 3, 0)):
        if (
            lines[i].strip() == "0"
            and lines[i + 1].strip().upper() == "SECTION"
            and lines[i + 2].strip() == "2"
            and lines[i + 3].strip().upper() == "ENTITIES"
        ):
            start = i + 4
            break
    if start is None:
        return None
    for i in range(start, max(len(lines) - 1, 0)):
        if lines[i].strip() == "0" and lines[i + 1].strip().upper() == "ENDSEC":
            return i
    return None


def _read_dxf_lines(filepath):
    for encoding in ("latin-1", "utf-8-sig", "utf-8"):
        try:
            with open(filepath, "r", encoding=encoding, errors="strict") as handle:
                return handle.read().splitlines()
        except Exception:
            continue
    with open(filepath, "r", encoding="latin-1", errors="replace") as handle:
        return handle.read().splitlines()


def _write_dxf_lines(filepath, lines):
    folder = os.path.dirname(filepath)
    if folder and not os.path.isdir(folder):
        os.makedirs(folder)
    with open(filepath, "w", encoding="latin-1", errors="replace", newline="\n") as handle:
        handle.write("\n".join(lines))
        handle.write("\n")


def _write_minimal_dxf(filepath):
    _write_dxf_lines(filepath, _minimal_dxf_lines())
    return os.path.exists(filepath)


def _inject_dxf_text(filepath, text_objs, scale_factor):
    entity_lines, text_count = _dxf_text_entities(text_objs, scale_factor)
    if not entity_lines:
        _warn("No se generaron entidades TEXT para insertar en DXF.")
        return False

    if not os.path.exists(filepath):
        _write_minimal_dxf(filepath)

    lines = _read_dxf_lines(filepath)
    insert_at = _find_entities_end_index(lines)
    if insert_at is None:
        _warn("DXF sin seccion ENTITIES valida. Se crea DXF minimo para textos.")
        lines = _minimal_dxf_lines()
        insert_at = _find_entities_end_index(lines)
    if insert_at is None:
        return False

    out = lines[:insert_at] + entity_lines + lines[insert_at:]
    _write_dxf_lines(filepath, out)
    _debug("TEXT nativo insertado en DXF: objetos_texto={} lineas_texto={} capa={}".format(
        len(text_objs),
        text_count,
        TEXT_DXF_LAYER,
    ))
    return True


def _file_signature(filepath):
    try:
        st = os.stat(filepath)
        return (int(st.st_size), int(getattr(st, "st_mtime_ns", int(st.st_mtime * 1000000000))))
    except Exception:
        return None


def _file_was_written(filepath, before_signature):
    after = _file_signature(filepath)
    if after is None:
        return False
    return after != before_signature and after[0] > 0


def _file_exists_nonempty(filepath):
    sig = _file_signature(filepath)
    return sig is not None and sig[0] > 0


def _remove_file(filepath):
    try:
        if filepath and os.path.exists(filepath):
            os.remove(filepath)
    except Exception:
        pass


def _temp_dxf_path(filepath):
    root, _ext = os.path.splitext(filepath)
    return root + "_ecr_tmp.dxf"


def _scaled_vector(vec, factor):
    return App.Vector(vec.x * factor, vec.y * factor, vec.z * factor)


def _text_lines(obj):
    try:
        text = getattr(obj, "Text", "")
    except Exception:
        text = ""
    if isinstance(text, (list, tuple)):
        lines = [_safe_text(line) for line in text]
    else:
        lines = _safe_text(text).splitlines()
    return lines or [""]


def _numeric_value(value):
    try:
        if hasattr(value, "Value"):
            return float(value.Value)
    except Exception:
        pass
    match = re.search(r"[-+]?\d+(?:[\.,]\d+)?", _safe_text(value))
    if not match:
        return None
    try:
        return float(match.group(0).replace(",", "."))
    except Exception:
        return None


def _copy_text_view_props(src, dst, scale_factor):
    try:
        src_vo = src.ViewObject
        dst_vo = dst.ViewObject
    except Exception:
        return

    for attr in ("FontName", "Justification", "DisplayMode", "DrawStyle", "TextColor"):
        try:
            if hasattr(src_vo, attr) and hasattr(dst_vo, attr):
                setattr(dst_vo, attr, getattr(src_vo, attr))
        except Exception:
            pass

    try:
        size = _numeric_value(getattr(src_vo, "FontSize", None))
        if size is not None and hasattr(dst_vo, "FontSize"):
            dst_vo.FontSize = "{} mm".format(size * scale_factor)
    except Exception:
        pass


def _resolve_text_font(src=None):
    candidates = []
    try:
        if src is not None and hasattr(src, "ViewObject"):
            font_file = _safe_text(getattr(src.ViewObject, "FontFile", ""))
            if font_file:
                candidates.append(font_file)
    except Exception:
        pass
    candidates.extend(
        [
            TEXT_OUTLINE_FONT,
            r"C:\Windows\Fonts\arial.ttf",
            r"C:\Windows\Fonts\calibri.ttf",
            r"C:\Windows\Fonts\segoeui.ttf",
        ]
    )
    for path in candidates:
        if path and os.path.isfile(path):
            return path
    return ""


def _text_font_size_mm(obj):
    try:
        size = _numeric_value(getattr(obj.ViewObject, "FontSize", None))
        if size is not None and size > 0:
            return size
    except Exception:
        pass
    return float(TEXT_DEFAULT_SIZE_MM)


def _make_shapestring_shape(text, font_file, size):
    if not _safe_text(text).strip() or not font_file:
        return None
    try:
        make_ss = getattr(Part, "makeShapeString", None)
        if make_ss:
            shp = make_ss(String=_safe_text(text), FontFile=font_file, Size=float(size), Tracking=0)
            if shp is not None and not getattr(shp, "isNull", lambda: False)():
                return shp
    except Exception as exc:
        _debug("Part.makeShapeString fallo: {}".format(exc))

    try:
        import Draft
        make_ds = getattr(Draft, "makeShapeString", None)
        if not make_ds:
            return None
        tmp = make_ds(String=_safe_text(text), FontFile=font_file, Size=float(size), Tracking=0)
        if tmp is None or not hasattr(tmp, "Shape"):
            return None
        shp = tmp.Shape.copy() if tmp.Shape else None
        try:
            App.ActiveDocument.removeObject(tmp.Name)
        except Exception:
            pass
        if shp is not None and not getattr(shp, "isNull", lambda: False)():
            return shp
    except Exception as exc:
        _debug("Draft.makeShapeString fallo: {}".format(exc))
    return None


def _text_outline_shape_scaled(obj, scale_factor):
    font_file = _resolve_text_font(obj)
    if not font_file:
        _warn("No se encontro fuente para convertir texto '{}' a contornos.".format(getattr(obj, "Label", obj.Name)))
        return None

    size = _text_font_size_mm(obj) * scale_factor
    line_height = size * float(TEXT_LINE_SPACING)
    lines = _text_lines(obj)
    line_shapes = []

    for idx, line in enumerate(lines):
        shp = _make_shapestring_shape(line, font_file, size)
        if shp is None or getattr(shp, "isNull", lambda: False)():
            continue
        try:
            shp.translate(App.Vector(0, -idx * line_height, 0))
        except Exception:
            pass
        line_shapes.append(shp)

    if not line_shapes:
        _warn("No se pudo convertir texto '{}' a contornos.".format(getattr(obj, "Label", obj.Name)))
        return None

    comp = _make_compound(line_shapes)
    if comp is None or getattr(comp, "isNull", lambda: False)():
        return None

    try:
        source_placement = obj.Placement
        base = _scaled_vector(source_placement.Base, scale_factor)
        rotation = source_placement.Rotation
        comp = comp.transformGeometry(App.Placement(base, rotation).toMatrix())
    except Exception as exc:
        _warn("No se pudo aplicar placement al texto '{}': {}".format(getattr(obj, "Label", obj.Name), exc))

    _debug("Texto convertido a contornos: origen={} lineas={} fuente={}".format(
        _safe_text(getattr(obj, "Label", getattr(obj, "Name", ""))),
        len(line_shapes),
        font_file,
    ))
    return comp


def _clone_text_scaled(obj, scale_factor):
    try:
        import Draft
    except Exception as exc:
        _warn("No se pudo cargar Draft para exportar texto: {}".format(exc))
        return None

    lines = _text_lines(obj)
    try:
        source_placement = obj.Placement
        base = _scaled_vector(source_placement.Base, scale_factor)
        rotation = source_placement.Rotation
    except Exception:
        base = App.Vector(0, 0, 0)
        rotation = App.Rotation()

    makers = (
        lambda: Draft.make_text(lines, point=base),
        lambda: Draft.make_text("\n".join(lines), point=base),
        lambda: Draft.make_text(lines, base),
        lambda: Draft.make_text("\n".join(lines), base),
        lambda: Draft.make_text(lines),
        lambda: Draft.make_text("\n".join(lines)),
    )

    text_obj = None
    for maker in makers:
        try:
            text_obj = maker()
            if text_obj is not None:
                break
        except Exception:
            continue

    if text_obj is None:
        _warn("No se pudo clonar texto '{}'.".format(getattr(obj, "Label", obj.Name)))
        return None

    try:
        text_obj.Label = getattr(obj, "Label", "Etiqueta")
    except Exception:
        pass
    try:
        text_obj.Placement = App.Placement(base, rotation)
    except Exception:
        pass
    _copy_text_view_props(obj, text_obj, scale_factor)
    _debug("Texto clonado para exportar: origen={} destino={} lineas={}".format(
        _safe_text(getattr(obj, "Label", getattr(obj, "Name", ""))),
        _safe_text(getattr(text_obj, "Name", "")),
        len(lines),
    ))
    return text_obj


def _export_items_scaled(shapes, text_objs, filepath, scale_factor):

    temp_doc = None
    prev_doc = App.ActiveDocument

    try:
        temp_doc = App.newDocument("Temp_DXF_Export")
        App.setActiveDocument(temp_doc.Name)

        ext = os.path.splitext(filepath)[1].lower()
        dxf_native_text = ext == ".dxf" and TEXT_AS_DXF_TEXT and bool(text_objs)

        temp_objs = []
        for i, shape in enumerate(shapes, start=1):
            if shape is None or shape.isNull():
                continue
            scaled = _scale_shape(shape, scale_factor)
            if scaled is None or scaled.isNull():
                continue
            tmp = temp_doc.addObject("Part::Feature", f"Tmp_{i}")
            tmp.Shape = scaled
            temp_objs.append(tmp)

        seen_text = set()
        for obj in text_objs:
            key = _object_key(obj)
            if key in seen_text:
                continue
            seen_text.add(key)
            if dxf_native_text:
                continue
            if TEXT_AS_OUTLINES:
                outline = _text_outline_shape_scaled(obj, scale_factor)
                if outline is not None and not outline.isNull():
                    tmp = temp_doc.addObject("Part::Feature", "Txt_{}".format(len(seen_text)))
                    tmp.Shape = outline
                    try:
                        tmp.Label = getattr(obj, "Label", tmp.Name)
                    except Exception:
                        pass
                    temp_objs.append(tmp)
                    continue

            tmp_text = _clone_text_scaled(obj, scale_factor)
            if tmp_text is not None:
                temp_objs.append(tmp_text)

        if not temp_objs and not dxf_native_text:
            _warn("No hay objetos exportables despues de aplicar escala.")
            return False

        before_signature = _file_signature(filepath)
        _debug("Export temporal: objetos={} geometria={} textos={} texto_dxf_nativo={} destino_existe={}".format(
            len(temp_objs),
            len(shapes),
            len(text_objs),
            int(dxf_native_text),
            int(before_signature is not None),
        ))

        if dxf_native_text:
            export_path = _temp_dxf_path(filepath)
            _remove_file(export_path)
            temp_before_signature = _file_signature(export_path)
            if temp_objs:
                temp_doc.recompute()
                _debug("DXF con textos nativos: exportando geometria a temporal con importDXF.")
                _try_dxf_export(temp_objs, export_path)
                if not _file_was_written(export_path, temp_before_signature):
                    _warn("importDXF no genero archivo nuevo. Probando ImportGui...")
                    _try_importgui_export(temp_objs, export_path)
                if not _file_exists_nonempty(export_path):
                    return False
            else:
                _debug("DXF solo con textos nativos: creando archivo DXF minimo.")
                if not _write_minimal_dxf(export_path):
                    return False
            if not _inject_dxf_text(export_path, text_objs, scale_factor):
                return False
            try:
                os.replace(export_path, filepath)
            except Exception as exc:
                _err("No se pudo reemplazar DXF final: {}".format(exc))
                return False
            _debug("DXF final actualizado desde temporal: {}".format(filepath))
            return _file_exists_nonempty(filepath)

        temp_doc.recompute()
        _try_importgui_export(temp_objs, filepath)
        if _file_was_written(filepath, before_signature):
            return True

        if ext == ".dxf":
            _warn("ImportGui no genero archivo nuevo. Probando exportador DXF alternativo...")
            _try_dxf_export(temp_objs, filepath)
            return _file_was_written(filepath, before_signature)

        return False

    except Exception as exc:
        _err(f"Fallo exportando: {exc}")
        return False

    finally:
        try:
            if prev_doc:
                App.setActiveDocument(prev_doc.Name)
        except Exception:
            pass
        try:
            if temp_doc:
                App.closeDocument(temp_doc.Name)
        except Exception:
            pass


# ----------------------------
# Main
# ----------------------------

def exportar_dxf_dwg_plano_trabajo():
    doc = App.ActiveDocument
    if doc is None:
        _err("No hay documento activo.")
        return

    wp = _get_workplane()
    if wp is None:
        if FALLBACK_Z0:
            _warn("No se encontro Working Plane. Usando plano XY (Z=0).")
            origin, normal = App.Vector(0, 0, 0), App.Vector(0, 0, 1)
        else:
            _err("No se encontro Working Plane (Draft).")
            return
    else:
        origin, normal = _plane_origin_normal(wp)

    selection = Gui.Selection.getSelection()
    flat = _flatten_selection(selection)
    selected_shapes, selected_texts = _collect_planar_exportables(flat, origin, normal, PLANE_TOL_MM)
    lighting_labels = _find_lighting_labels(doc, origin, normal, PLANE_TOL_MM)

    selected_count = len(selected_shapes) + len(selected_texts)
    options = _show_export_options_dialog(selected_count, len(lighting_labels))
    if options is None:
        _warn("Exportacion cancelada.")
        return

    planar_shapes = []
    text_objs = []
    seen_text = set()

    if options.get("selection"):
        planar_shapes.extend(selected_shapes)
        for obj in selected_texts:
            key = _object_key(obj)
            if key not in seen_text:
                seen_text.add(key)
                text_objs.append(obj)

    if options.get("lighting_labels"):
        for obj in lighting_labels:
            key = _object_key(obj)
            if key not in seen_text:
                seen_text.add(key)
                text_objs.append(obj)

    if not planar_shapes and not text_objs:
        _warn("No hay elementos para exportar con las opciones seleccionadas.")
        return

    filepath = _pick_output_path(doc)
    if not filepath:
        _warn("Exportacion cancelada.")
        return

    ok = _export_items_scaled(planar_shapes, text_objs, filepath, SCALE_FACTOR)
    if ok:
        _log("Exportado: {} | geometria={} | textos={}".format(filepath, len(planar_shapes), len(text_objs)))
    else:
        _err("No se pudo exportar el archivo.")


if __name__ == "__main__":
    exportar_dxf_dwg_plano_trabajo()

# -*- coding: utf-8 -*-
# MenuText: Conectar Alimentadores...
# ToolTip: Conecta circuitos o equipos con su tablero asignado; las guias seleccionadas son opcionales
# Icon: Conectar/Conectar_Alimentadores_a_Tablero_Auto.svg
# Toolbar: Conectar
# Transaction: self

"""Comando general de alimentadores ElectricCR.

Reemplaza como interfaz normal las variantes TP, TCOM, tablero-tablero y HVAC.
La geometria vive en ``ElectricCR.electriccr.connections``. Una guia
seleccionada se usa de forma preferente; sin guia se genera una ruta directa.
Compatible con FreeCAD 1.1.3. Revision: 2026-08-08 18:01 CST.
No agregar motores TP/TCOM aqui; este archivo solo adapta la interfaz.
"""

from pathlib import Path
import sys

import FreeCAD as App

try:
    import FreeCADGui as Gui
except Exception:
    Gui = None


def _load_services():
    root = Path(__file__).resolve().parent.parent
    if str(root) not in sys.path:
        sys.path.insert(0, str(root))
    from ElectricCR.electriccr.connections import assignments, feeders, panels, routing

    return assignments, feeders, panels, routing


def _selection():
    if Gui is None:
        return []
    try:
        return list(Gui.Selection.getSelection() or [])
    except Exception:
        return []


def _default_cfg():
    prefs = App.ParamGet("User parameter:BaseApp/Preferences/Mod/ElectricCR/ConectarAlimentadores")
    return {
        "route_z": float(prefs.GetFloat("route_z", 3400.0)),
        "lane_spacing": float(prefs.GetFloat("lane_spacing", 50.0)),
        "approach_clearance": float(prefs.GetFloat("approach_clearance", 300.0)),
        "bend_radius": float(prefs.GetFloat("bend_radius", 100.0)),
        "port_stub": float(prefs.GetFloat("port_stub", 80.0)),
        "diameter": float(prefs.GetFloat("diameter", 22.2)),
    }


def _dialog(cfg, guide_count):
    if Gui is None:
        return cfg
    QtWidgets = None
    for binding in ("PySide6", "PySide2"):
        try:
            QtWidgets = __import__(binding, fromlist=["QtWidgets"]).QtWidgets
            break
        except Exception:
            pass
    if QtWidgets is None:
        return cfg
    dialog = QtWidgets.QDialog(Gui.getMainWindow())
    dialog.setWindowTitle("Conectar Alimentadores")
    dialog.setMinimumWidth(520)
    info = QtWidgets.QLabel(
        "Guias seleccionadas: {}. Si ninguna resulta aplicable, el motor continua en modo DIRECTO.".format(guide_count)
    )
    info.setWordWrap(True)
    form = QtWidgets.QFormLayout()
    controls = {}
    for key, label, minimum, maximum in (
        ("route_z", "Altura de ruta:", 0.0, 20000.0),
        ("lane_spacing", "Separacion de carriles:", 10.0, 1000.0),
        ("approach_clearance", "Separacion al tablero:", 0.0, 5000.0),
        ("bend_radius", "Radio de curvas:", 0.0, 2000.0),
        ("port_stub", "Salida recta de puerto:", 0.0, 1000.0),
        ("diameter", "Diametro EMT:", 1.0, 300.0),
    ):
        control = QtWidgets.QDoubleSpinBox()
        control.setRange(minimum, maximum)
        control.setDecimals(1)
        control.setSuffix(" mm")
        control.setValue(float(cfg[key]))
        controls[key] = control
        form.addRow(label, control)
    buttons = QtWidgets.QDialogButtonBox(QtWidgets.QDialogButtonBox.Ok | QtWidgets.QDialogButtonBox.Cancel)
    buttons.accepted.connect(dialog.accept)
    buttons.rejected.connect(dialog.reject)
    layout = QtWidgets.QVBoxLayout(dialog)
    layout.addWidget(info)
    layout.addLayout(form)
    layout.addWidget(buttons)
    execute = getattr(dialog, "exec", None) or getattr(dialog, "exec_", None)
    if execute() != QtWidgets.QDialog.Accepted:
        return None
    prefs = App.ParamGet("User parameter:BaseApp/Preferences/Mod/ElectricCR/ConectarAlimentadores")
    for key, control in controls.items():
        cfg[key] = float(control.value())
        prefs.SetFloat(key, cfg[key])
    return cfg


def run(doc_override=None, cfg_override=None, selection_override=None, panel_code=None, circuit_prefix=None):
    assignments, feeders, panels, routing = _load_services()
    doc = doc_override or App.ActiveDocument
    if doc is None:
        App.Console.PrintWarning("[ElectricCR][FEEDER] No hay documento activo.\n")
        return None
    selected = list(selection_override) if selection_override is not None else _selection()
    selected_panels = [obj for obj in selected if panels.is_panel(obj)]
    selected_groups = [obj for obj in selected if panels.is_group(obj)]
    guides = [
        obj for obj in selected
        if obj not in selected_panels and obj not in selected_groups and routing.is_guide(obj, explicit=True)
    ]
    equipment = [
        obj for obj in selected
        if obj not in selected_panels and assignments.is_connectable_equipment(obj)
    ]
    forced_panel = selected_panels[0] if len(selected_panels) == 1 else None
    if forced_panel is None and panel_code:
        forced_panel = panels.find_panel_by_token(doc, panel_code)

    cfg = dict(cfg_override) if cfg_override is not None else _dialog(_default_cfg(), len(guides))
    if cfg is None:
        return None

    result = {"circuits": None, "equipment": None}
    # Sin seleccion de equipos, el comando trabaja con circuitos. Seleccionar
    # grupos limita el alcance; sin grupos procesa todos los circuitos asignados.
    if not equipment:
        result["circuits"] = feeders.connect_circuit_feeders(
            doc,
            circuit_groups=selected_groups or None,
            forced_panel=forced_panel,
            panel_code=panel_code,
            guides=guides,
            cfg=cfg,
            circuit_prefix=circuit_prefix,
        )
    else:
        records = assignments.analyze_equipment(doc, equipment)
        valid = [record for record in records if record.get("panel") is not None and record.get("circuit_id")]
        doc.openTransaction("ElectricCR: sincronizar asignaciones de alimentadores")
        try:
            for record in valid:
                assignments.sync_equipment_assignment(
                    record["object"], record["panel"], record["circuit_id"], feeders.GENERATED_BY
                )
            doc.recompute()
            doc.commitTransaction()
        except Exception:
            doc.abortTransaction()
            raise
        result["equipment"] = feeders.connect_equipment_feeders(doc, records, guides=guides, cfg=cfg)
    return result


def main():
    return run()


if __name__ == "__main__":
    main()

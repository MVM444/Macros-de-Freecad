# -*- coding: utf-8 -*-
# MenuText: Poligonos de recintos desde muros BIM
# ToolTip: Genera areas poligonales desde los huecos cerrados de muros Arch/BIM.
# Icon: PoligonosRecintosDesdeArchWalls.svg
# Version: 1.4.0
# Revision: 2026-09-22 13:25:00 America/Costa_Rica
# FreeCAD: 1.1.3

"""Create independent polygonal room areas from Arch/BIM wall footprints.

The macro never edits rectangular areas, source walls or selected auxiliary solids.
It accepts multiple BIM walls plus explicitly selected columns/pillars/solids.
Room detection is level-aware. Native BIM Building Storey containment is the
authority for walls; a wall's FA_TargetLevel is diagnostic only. Columns and
other auxiliary solids participate when their vertical extent crosses the
analysis level. Wall barriers prefer ArchWall.getExtrusionData(), which returns
the nominal unperforated wall base before door/window subtractions; the current
wall Shape is only a fallback. Connected free-space detection keeps the validated
fuzzy topological cut for T-junctions. Outputs, schedules and DEBUG geometry are
scoped per level, so recalculating one storey never deletes another storey's
room polygons.
"""

from __future__ import annotations

import math
import re

import Draft
import FreeCAD as App
import FreeCADGui as Gui
import Part


MACRO_ID = "FA_PolygonalRoomsFromArchWalls"
GROUP_NAME = "FA_PolygonalRooms"
GROUP_LABEL = "Recintos poligonales desde muros BIM"
SHEET_NAME = "Spreadsheet_PolygonalRooms"
MIN_ROOM_AREA_M2 = 1.0
DISPLAY_ELEVATION_MM = 20.0
GEOMETRY_TOLERANCE_MM = 0.1
CLOSURE_CONTACT_TOLERANCE_MM = 1.0
MACRO_VERSION = "1.4.0"
SUSPICIOUS_ROOM_MIN_AREA_M2 = 50.0
SUSPICIOUS_ROOM_RATIO = 8.0
FREE_SPACE_FRAME_MARGIN_MM = 2000.0
FREE_SPACE_FRAME_MARGIN_RATIO = 0.10
TOPOLOGY_FUZZY_TOLERANCE_MM = 0.5
DEBUG_GEOMETRY = True
DEBUG_GROUP_NAME_PREFIX = "FA_PolygonalRooms_DEBUG_"
DEBUG_GROUP_LABEL_PREFIX = "DEBUG - Deteccion de recintos"
LEVEL_GROUP_NAME_PREFIX = "FA_PolygonalRooms_Level_"
SHEET_NAME_PREFIX = "Spreadsheet_PolygonalRooms_"
LEVEL_Z_TOLERANCE_MM = 0.5


def log(message):
    App.Console.PrintMessage("[FACILARQ][POLIGONOS] " + str(message) + "\n")


def warn(message):
    App.Console.PrintWarning("[FACILARQ][POLIGONOS] " + str(message) + "\n")


def error(message):
    App.Console.PrintError("[FACILARQ][POLIGONOS] " + str(message) + "\n")


def set_property(obj, property_type, name, group, description, value):
    if not hasattr(obj, name):
        obj.addProperty(property_type, name, group, description)
    try:
        setattr(obj, name, value)
    except Exception as exc:
        warn("No se pudo asignar %s en %s: %s" % (name, object_label(obj), exc))


def object_label(obj):
    return str(getattr(obj, "Label", getattr(obj, "Name", "")) or "")


def is_group(obj):
    if obj is None:
        return False
    try:
        return bool(
            obj.isDerivedFrom("App::DocumentObjectGroup")
            or obj.isDerivedFrom("App::Part")
        )
    except Exception:
        return hasattr(obj, "Group") and not has_shape(obj) if "has_shape" in globals() else hasattr(obj, "Group")


def flatten_objects(objects):
    pending = list(objects or [])
    result = []
    seen = set()
    while pending:
        obj = pending.pop(0)
        identity = str(getattr(obj, "Name", "") or id(obj))
        if identity in seen:
            continue
        seen.add(identity)
        result.append(obj)
        for attribute in ("Group", "Objects"):
            try:
                pending.extend(list(getattr(obj, attribute, []) or []))
            except Exception:
                pass
    return result


def has_shape(obj):
    try:
        return obj.Shape is not None and not obj.Shape.isNull() and bool(obj.Shape.Faces)
    except Exception:
        return False


def is_arch_wall(obj):
    if obj is None or not has_shape(obj):
        return False
    role = str(getattr(obj, "FA_Role", "") or "").strip().lower()
    ifc_type = str(getattr(obj, "IfcType", "") or "").strip().lower()
    proxy_type = str(getattr(getattr(obj, "Proxy", None), "Type", "") or "").strip().lower()
    type_id = str(getattr(obj, "TypeId", "") or "").lower()
    text = (str(getattr(obj, "Name", "")) + " " + object_label(obj)).lower()
    return bool(
        role == "wall"
        or ifc_type in ("wall", "wallstandardcase")
        or proxy_type == "wall"
        or "arch::wall" in type_id
        or ("muro bim" in text and "wall" in str(getattr(obj, "Name", "")).lower())
    )


def is_column_like(obj):
    """Detect column/pillar semantics when the object came from an expanded group."""
    if obj is None or is_group(obj) or is_arch_wall(obj) or not has_shape(obj):
        return False
    role = str(getattr(obj, "FA_Role", "") or "").strip().lower()
    ifc_type = str(getattr(obj, "IfcType", "") or "").strip().lower()
    proxy_type = str(getattr(getattr(obj, "Proxy", None), "Type", "") or "").strip().lower()
    text = (str(getattr(obj, "Name", "")) + " " + object_label(obj)).lower()
    tokens = ("column", "columna", "pillar", "pilar")
    return bool(
        role in ("column", "columns", "pillar", "pillars", "structural_column", "obstacle")
        or ifc_type in ("column", "pillar")
        or proxy_type in ("column", "pillar")
        or any(token in text for token in tokens)
    )


def is_selected_obstacle(obj, explicitly_selected=False):
    """Accept explicit shaped objects as obstacles; descendants require column semantics."""
    if obj is None or is_group(obj) or is_arch_wall(obj) or not has_shape(obj):
        return False
    if str(getattr(obj, "FA_GeneratedBy", "") or "") == MACRO_ID:
        return False
    type_id = str(getattr(obj, "TypeId", "") or "").lower()
    if "spreadsheet" in type_id or "annotation" in type_id:
        return False
    if explicitly_selected:
        return True
    return is_column_like(obj)


def is_bim_level(obj):
    """Return True for native BIM storeys used as architectural levels."""
    if obj is None:
        return False
    role = str(getattr(obj, "FA_Role", "") or "").strip().lower()
    ifc_type = str(getattr(obj, "IfcType", "") or "").strip().lower()
    return role == "level" or ifc_type in ("building storey", "buildingstorey", "ifcbuildingstorey")


def level_elevation_mm(level):
    """Read the storey elevation, preferring the native Elevation property."""
    if level is None:
        return 0.0
    try:
        return float(getattr(level.Elevation, "Value", level.Elevation))
    except Exception:
        pass
    try:
        return float(level.Placement.Base.z)
    except Exception:
        return 0.0


def level_members(level):
    """Return all descendants of a Building Storey without including the storey itself."""
    if level is None:
        return []
    return flatten_objects(list(getattr(level, "Group", []) or []))


def object_native_levels(doc, obj):
    """Resolve native Building Storey containment from Group membership."""
    if obj is None:
        return []
    result = []
    for level in [candidate for candidate in doc.Objects if is_bim_level(candidate)]:
        try:
            if obj in level_members(level):
                result.append(level)
        except Exception:
            pass
    return unique_objects(result)


def architectural_levels(doc):
    """Return Building Storeys that actually contain BIM walls.

    Chomes contains several auxiliary/legacy Building Storeys at Z=0. A storey
    becomes an Areas analysis candidate only when its native Group hierarchy
    contains at least one wall. This avoids guessing from labels or stale
    FA_TargetLevel strings.
    """
    result = []
    for level in [candidate for candidate in doc.Objects if is_bim_level(candidate)]:
        if any(is_arch_wall(obj) for obj in level_members(level)):
            result.append(level)
    result.sort(key=lambda item: (level_elevation_mm(item), object_label(item), str(getattr(item, "Name", ""))))
    return result


def _is_visible(obj):
    try:
        return bool(obj.ViewObject.Visibility)
    except Exception:
        return True


def object_crosses_level(obj, elevation_mm, tolerance=LEVEL_Z_TOLERANCE_MM):
    """True when a shaped object physically crosses the storey analysis plane.

    The upper bound is exclusive so an element ending exactly at the next level
    does not leak into that level. This is primarily used for columns that are
    grouped under the first storey but continue through upper storeys.
    """
    if not has_shape(obj):
        return False
    try:
        bounds = obj.Shape.BoundBox
        zmin = float(bounds.ZMin)
        zmax = float(bounds.ZMax)
    except Exception:
        return False
    z = float(elevation_mm)
    tol = max(float(tolerance), 0.0)
    return z >= zmin - tol and z < zmax - tol


def resolve_analysis_level(doc, raw_selection=None, walls_hint=None, explicit_level=None):
    """Resolve one authoritative storey for the Areas calculation."""
    levels = architectural_levels(doc)
    if explicit_level is not None:
        if not is_bim_level(explicit_level):
            raise RuntimeError("El nivel indicado no es un Building Storey BIM valido.")
        return explicit_level

    selection = list(raw_selection if raw_selection is not None else (Gui.Selection.getSelection() or []))
    selected_levels = unique_objects([obj for obj in selection if is_bim_level(obj)])
    if len(selected_levels) > 1:
        raise RuntimeError("Seleccione un solo nivel BIM para calcular Areas.")

    selected_walls = [obj for obj in flatten_objects(selection) if is_arch_wall(obj)]
    hinted_walls = [obj for obj in list(walls_hint or []) if is_arch_wall(obj)]
    wall_levels = []
    for wall in unique_objects(selected_walls + hinted_walls):
        wall_levels.extend(object_native_levels(doc, wall))
    wall_levels = unique_objects(wall_levels)

    if selected_levels:
        level = selected_levels[0]
        conflicting = [item for item in wall_levels if item is not level]
        if conflicting:
            raise RuntimeError(
                "La seleccion mezcla el nivel '%s' con muros contenidos en otro nivel."
                % object_label(level)
            )
        return level

    if len(wall_levels) == 1:
        return wall_levels[0]
    if len(wall_levels) > 1:
        raise RuntimeError("La seleccion contiene muros de varios niveles. Seleccione un solo piso.")

    visible_level_candidates = []
    for level in levels:
        level_walls = [obj for obj in level_members(level) if is_arch_wall(obj)]
        if any(_is_visible(wall) for wall in level_walls):
            visible_level_candidates.append(level)
    if len(visible_level_candidates) == 1:
        return visible_level_candidates[0]
    if len(levels) == 1:
        return levels[0]
    if not levels:
        raise RuntimeError("No se encontraron Building Storeys BIM que contengan muros.")

    names = ", ".join("%s [%s]" % (object_label(level), level.Name) for level in levels)
    raise RuntimeError(
        "Hay varios niveles BIM con muros (%s). Seleccione el nivel o un muro del piso que desea calcular."
        % names
    )


def tag_level_metadata(obj, level):
    """Attach stable level identity to generated objects without mutating source BIM."""
    if obj is None or level is None:
        return
    elevation = level_elevation_mm(level)
    set_property(obj, "App::PropertyLink", "FA_Level", "FacilArquitectura", "Nivel BIM asociado", level)
    set_property(obj, "App::PropertyString", "FA_LevelName", "FacilArquitectura", "Nombre interno del nivel", str(level.Name))
    set_property(obj, "App::PropertyString", "FA_LevelLabel", "FacilArquitectura", "Etiqueta del nivel", object_label(level))
    set_property(obj, "App::PropertyLength", "FA_LevelElevation", "FacilArquitectura", "Elevacion del nivel", elevation)


def collect_sources(doc, level=None, walls_hint=None):
    """Collect one storey's walls plus level-crossing auxiliary barriers.

    Native Building Storey containment is authoritative for walls. GUI selection
    chooses the storey but does not restrict it to a partial wall subset. Visible
    walls in that storey are the normal boundary base; selected hidden walls in
    the same storey are additive. Visible columns/pillars that physically cross
    the storey elevation are included automatically even if their native Group is
    under another storey. Explicitly selected shaped auxiliaries are also admitted
    when they cross the analysis plane.
    """
    raw_selection = list(Gui.Selection.getSelection() or [])
    expanded = flatten_objects(raw_selection)
    level = resolve_analysis_level(doc, raw_selection, walls_hint=walls_hint, explicit_level=level)
    elevation = level_elevation_mm(level)
    members = level_members(level)
    native_walls = unique_objects([obj for obj in members if is_arch_wall(obj)])
    if not native_walls:
        raise RuntimeError("El nivel '%s' no contiene muros BIM." % object_label(level))

    visible_walls = [wall for wall in native_walls if _is_visible(wall)]
    selected_walls = unique_objects([obj for obj in expanded if is_arch_wall(obj)])
    foreign_selected = [wall for wall in selected_walls if wall not in native_walls]
    if foreign_selected:
        raise RuntimeError(
            "Hay muros seleccionados fuera del nivel '%s': %s"
            % (object_label(level), ", ".join(object_label(wall) for wall in foreign_selected))
        )

    if visible_walls:
        walls = unique_objects(visible_walls + selected_walls)
        wall_source = "muros visibles del nivel"
    else:
        walls = native_walls
        wall_source = "muros del nivel (sin visibles)"
        warn(
            "El nivel '%s' no tiene muros visibles; se usaran sus %d muros BIM contenidos."
            % (object_label(level), len(walls))
        )

    # Diagnose stale FA metadata, but never rewrite source objects here.
    for wall in walls:
        target = str(getattr(wall, "FA_TargetLevel", "") or "")
        if target and target != str(level.Name):
            warn(
                "Metadato de nivel desactualizado: %s | FA_TargetLevel=%s | nivel_nativo=%s. "
                "Areas usara la contencion BIM nativa."
                % (object_label(wall), target, level.Name)
            )
        try:
            bounds = wall.Shape.BoundBox
            if not (elevation >= float(bounds.ZMin) - LEVEL_Z_TOLERANCE_MM and elevation < float(bounds.ZMax) - LEVEL_Z_TOLERANCE_MM):
                warn(
                    "Muro contenido en '%s' no cruza geometricamente su cota %.3f mm: %s | Z=%.3f..%.3f"
                    % (object_label(level), elevation, object_label(wall), float(bounds.ZMin), float(bounds.ZMax))
                )
        except Exception:
            pass

    direct_names = {str(getattr(obj, "Name", "") or "") for obj in raw_selection}
    selected_aux = unique_objects(
        [
            obj
            for obj in expanded
            if is_selected_obstacle(
                obj,
                explicitly_selected=str(getattr(obj, "Name", "") or "") in direct_names,
            )
        ]
    )
    selected_aux = [obj for obj in selected_aux if object_crosses_level(obj, elevation)]

    automatic_columns = []
    for obj in doc.Objects:
        if not is_column_like(obj) or not _is_visible(obj):
            continue
        if object_crosses_level(obj, elevation):
            automatic_columns.append(obj)
    obstacles = unique_objects(automatic_columns + selected_aux)

    parts = [wall_source]
    if automatic_columns:
        parts.append("columnas que cruzan el nivel")
    extra_selected = [obj for obj in selected_aux if obj not in automatic_columns]
    if extra_selected:
        parts.append("auxiliares seleccionados")
    source_mode = " + ".join(parts)

    log(
        "Nivel de analisis: %s [%s] | elevacion=%.3f mm | muros=%d | columnas_cruzan=%d | auxiliares=%d"
        % (
            object_label(level),
            level.Name,
            elevation,
            len(walls),
            len(automatic_columns),
            len(extra_selected),
        )
    )
    return walls, obstacles, bool(raw_selection), source_mode, level


def collect_walls(doc):
    """Backward-compatible wall-only wrapper for the resolved analysis level."""
    walls, _obstacles, selected_mode, _source_mode, _level = collect_sources(doc)
    return walls, selected_mode


def unique_objects(objects):
    result = []
    seen = set()
    for obj in objects:
        name = str(getattr(obj, "Name", "") or id(obj))
        if name in seen:
            continue
        seen.add(name)
        result.append(obj)
    return result


def face_is_horizontal_top(face, top_z):
    bounds = face.BoundBox
    if abs(float(bounds.ZMin) - float(top_z)) > GEOMETRY_TOLERANCE_MM:
        return False
    if abs(float(bounds.ZMax) - float(top_z)) > GEOMETRY_TOLERANCE_MM:
        return False
    try:
        u0, u1, v0, v1 = face.ParameterRange
        normal = face.normalAt((u0 + u1) * 0.5, (v0 + v1) * 0.5)
        return float(normal.z) > 0.999
    except Exception:
        return False


def projected_top_faces(obj):
    """Project horizontal top faces of a shaped object to the XY plane."""
    shape = obj.Shape
    solids = list(shape.Solids)
    sources = solids if solids else [shape]
    result = []
    for solid in sources:
        top_z = float(solid.BoundBox.ZMax)
        top_faces = [face for face in solid.Faces if face_is_horizontal_top(face, top_z)]
        for face in top_faces:
            projected = face.copy()
            projected.translate(App.Vector(0.0, 0.0, -top_z))
            result.append(projected)
    if not result:
        raise RuntimeError(
            "El objeto %s no tiene caras superiores horizontales proyectables."
            % object_label(obj)
        )
    return result


def _fuse_faces(faces):
    if not faces:
        return None
    result = faces[0]
    for face in faces[1:]:
        result = result.fuse(face)
    try:
        result = result.removeSplitter()
    except Exception:
        pass
    return result


def nominal_wall_footprint_faces(wall):
    """Return the unperforated native Arch wall base projected to Z=0.

    ArchWall.getExtrusionData() is the same native path used by FreeCAD to build
    the wall before Additions/Subtractions (doors, windows, openings). This is a
    better room-boundary authority than the final perforated Shape. If a wall
    proxy cannot provide extrusion data, fall back to the validated top-face
    projection used by v1.3.x.
    """
    proxy = getattr(wall, "Proxy", None)
    if proxy is not None and hasattr(proxy, "getExtrusionData"):
        try:
            data = proxy.getExtrusionData(wall)
            if data:
                raw_faces = data[0] if isinstance(data[0], (list, tuple)) else [data[0]]
                placement = data[2]
                placements = list(placement) if isinstance(placement, (list, tuple)) else [placement] * len(raw_faces)
                projected = []
                for index, face in enumerate(raw_faces):
                    copy = face.copy()
                    pl = placements[index] if index < len(placements) else placements[-1]
                    copy.Placement = pl.multiply(copy.Placement)
                    copy.translate(App.Vector(0.0, 0.0, -float(copy.BoundBox.ZMin)))
                    if copy.isValid() and float(copy.Area) > 0.0:
                        projected.append(copy)
                if projected:
                    log(
                        "Huella muro %s: metodo=ArchWall.getExtrusionData | caras=%d"
                        % (object_label(wall), len(projected))
                    )
                    return projected, "ArchWall.getExtrusionData"
        except Exception as exc:
            warn(
                "Huella nominal no disponible para '%s'; se usa Shape final como respaldo: %s"
                % (object_label(wall), exc)
            )
    faces = projected_top_faces(wall)
    log("Huella muro %s: metodo=ShapeTopFallback | caras=%d" % (object_label(wall), len(faces)))
    return faces, "ShapeTopFallback"


def fuse_wall_footprints(walls):
    faces = []
    methods = {}
    for wall in walls:
        wall_faces, method = nominal_wall_footprint_faces(wall)
        faces.extend(wall_faces)
        methods[method] = methods.get(method, 0) + 1
    if not faces:
        raise RuntimeError("No fue posible obtener la huella nominal de los muros.")
    footprint = _fuse_faces(faces)
    if footprint is None or footprint.isNull() or not footprint.Faces:
        raise RuntimeError("La union de huellas de muro no produjo caras planas.")
    log(
        "Huellas de muro: caras=%d | nominales=%d | fallback_shape=%d"
        % (
            len(faces),
            methods.get("ArchWall.getExtrusionData", 0),
            methods.get("ShapeTopFallback", 0),
        )
    )
    return footprint, len(faces)


def projected_top_components(obj):
    """Project each connected solid/top component independently to XY.

    A single Arch Structure can contain many columns. Keeping one projected
    component per solid lets the macro classify each column independently as a
    wall-closing element or as an isolated interior obstacle.
    """
    shape = obj.Shape
    solids = list(shape.Solids)
    sources = solids if solids else [shape]
    components = []
    face_count = 0
    for source in sources:
        top_z = float(source.BoundBox.ZMax)
        top_faces = [face for face in source.Faces if face_is_horizontal_top(face, top_z)]
        if not top_faces:
            continue
        projected = []
        for face in top_faces:
            copy = face.copy()
            copy.translate(App.Vector(0.0, 0.0, -top_z))
            projected.append(copy)
        footprint = _fuse_faces(projected)
        if footprint is None or footprint.isNull() or not list(getattr(footprint, "Faces", []) or []):
            continue
        components.append(footprint)
        face_count += len(top_faces)
    if not components:
        raise RuntimeError(
            "El objeto %s no tiene caras superiores horizontales proyectables."
            % object_label(obj)
        )
    return components, face_count


def obstacle_footprints(obstacles):
    """Return projected components for selected auxiliary objects."""
    entries = []
    face_count = 0
    for obj in unique_objects(obstacles):
        try:
            components, count = projected_top_components(obj)
            for index, footprint in enumerate(components, 1):
                entries.append(
                    {
                        "object": obj,
                        "shape": footprint,
                        "component_index": index,
                    }
                )
            face_count += count
        except Exception as exc:
            warn("Obstaculo omitido '%s': %s" % (object_label(obj), exc))
    return entries, face_count


def _shape_contact_distance(first, second):
    try:
        return float(first.distToShape(second)[0])
    except Exception:
        return None


def shapes_touch_or_intersect(first, second, tolerance=CLOSURE_CONTACT_TOLERANCE_MM):
    """True when two planar footprints overlap or touch within tolerance."""
    try:
        common = first.common(second)
        if common is not None and not common.isNull():
            if (
                list(getattr(common, "Faces", []) or [])
                or list(getattr(common, "Edges", []) or [])
                or list(getattr(common, "Vertexes", []) or [])
            ):
                return True
    except Exception:
        pass
    distance = _shape_contact_distance(first, second)
    return distance is not None and distance <= float(tolerance)


def classify_auxiliary_components(wall_footprint, entries):
    """Split selected components into wall closures and isolated obstacles."""
    closures = []
    interiors = []
    for entry in list(entries or []):
        footprint = entry["shape"]
        distance = _shape_contact_distance(wall_footprint, footprint)
        is_closure = shapes_touch_or_intersect(wall_footprint, footprint)
        target = closures if is_closure else interiors
        target.append(entry)
        distance_text = "n/a" if distance is None else "%.3f mm" % distance
        log(
            "Auxiliar %s#%02d: %s | distancia_muro=%s"
            % (
                object_label(entry["object"]),
                int(entry.get("component_index", 0) or 0),
                "CIERRE" if is_closure else "INTERIOR",
                distance_text,
            )
        )
    return closures, interiors


def fuse_closure_footprints(wall_footprint, closure_entries):
    """Fuse wall-touching auxiliary footprints and record their real contribution."""
    result = wall_footprint
    for entry in list(closure_entries or []):
        before = shape_area(result)
        try:
            fused = result.fuse(entry["shape"])
            try:
                fused = fused.removeSplitter()
            except Exception:
                pass
        except Exception as exc:
            warn(
                "No se pudo fusionar cierre %s#%02d: %s"
                % (
                    object_label(entry["object"]),
                    int(entry.get("component_index", 0) or 0),
                    exc,
                )
            )
            entry["closure_added_area"] = 0.0
            entry["closure_applied"] = False
            continue
        after = shape_area(fused)
        added = max(0.0, after - before)
        entry["closure_added_area"] = added
        entry["closure_applied"] = True
        result = fused
        log(
            "Cierre aplicado %s#%02d: area_agregada=%.4f m2"
            % (
                object_label(entry["object"]),
                int(entry.get("component_index", 0) or 0),
                added / 1000000.0,
            )
        )
    try:
        result = result.removeSplitter()
    except Exception:
        pass
    if result is None or result.isNull() or not list(getattr(result, "Faces", []) or []):
        raise RuntimeError("La union de muros y elementos de cierre no produjo una huella valida.")
    return result


def closure_sources_for_room(room_face, closure_entries):
    """Return closure objects geometrically associated with this room boundary."""
    result = []
    seen = set()
    boundary = getattr(room_face, "OuterWire", room_face)
    for entry in list(closure_entries or []):
        if not entry.get("closure_applied", True):
            continue
        footprint = entry["shape"]
        distances = [
            _shape_contact_distance(boundary, footprint),
            _shape_contact_distance(room_face, footprint),
        ]
        usable = [value for value in distances if value is not None]
        if not usable or min(usable) > CLOSURE_CONTACT_TOLERANCE_MM:
            continue
        obj = entry["object"]
        name = str(getattr(obj, "Name", "") or id(obj))
        if name in seen:
            continue
        seen.add(name)
        result.append(obj)
    return result


def shape_area(shape):
    try:
        return float(shape.Area)
    except Exception:
        return sum(float(face.Area) for face in list(getattr(shape, "Faces", []) or []))


def shape_perimeter(shape):
    total = 0.0
    for face in list(getattr(shape, "Faces", []) or []):
        for wire in list(getattr(face, "Wires", []) or []):
            total += float(wire.Length)
    return total


def subtract_obstacles(room_face, obstacle_entries):
    """Cut isolated selected components from one room face."""
    result = room_face.copy()
    used = []
    seen = set()
    removed_area = 0.0
    for entry in list(obstacle_entries or []):
        obj = entry["object"]
        footprint = entry["shape"]
        try:
            overlap = result.common(footprint)
            overlap_area = shape_area(overlap)
        except Exception as exc:
            warn("No se pudo intersectar '%s' con el recinto: %s" % (object_label(obj), exc))
            continue
        if overlap_area <= max(GEOMETRY_TOLERANCE_MM * GEOMETRY_TOLERANCE_MM, 0.01):
            continue
        before = shape_area(result)
        try:
            cut = result.cut(footprint)
            try:
                cut = cut.removeSplitter()
            except Exception:
                pass
            after = shape_area(cut)
            if cut.isNull() or not list(getattr(cut, "Faces", []) or []) or after <= 0.0:
                warn("El obstaculo '%s' eliminaria todo el recinto; se omitio." % object_label(obj))
                continue
            result = cut
            name = str(getattr(obj, "Name", "") or id(obj))
            if name not in seen:
                seen.add(name)
                used.append(obj)
            removed_area += max(0.0, before - after)
        except Exception as exc:
            warn("No se pudo restar '%s' del recinto: %s" % (object_label(obj), exc))
    return result, used, removed_area


def same_wire(first, second):
    try:
        return bool(first.isSame(second))
    except Exception:
        return first.hashCode() == second.hashCode()


def _analysis_frame(barrier_reference):
    """Create a temporary planar frame that safely surrounds all barriers."""
    bounds = barrier_reference.BoundBox
    span = max(float(bounds.XLength), float(bounds.YLength), 1.0)
    margin = max(float(FREE_SPACE_FRAME_MARGIN_MM), span * float(FREE_SPACE_FRAME_MARGIN_RATIO))
    x0 = float(bounds.XMin) - margin
    y0 = float(bounds.YMin) - margin
    width = max(1.0, float(bounds.XLength) + 2.0 * margin)
    height = max(1.0, float(bounds.YLength) + 2.0 * margin)
    frame = Part.makePlane(width, height, App.Vector(x0, y0, 0.0))
    return frame, margin


def _face_touches_frame_boundary(face, frame, tolerance=GEOMETRY_TOLERANCE_MM):
    """Return True only for free-space faces connected to the analysis exterior."""
    bounds = face.BoundBox
    frame_bounds = frame.BoundBox
    tolerance = max(float(tolerance), 0.01)
    return bool(
        abs(float(bounds.XMin) - float(frame_bounds.XMin)) <= tolerance
        or abs(float(bounds.XMax) - float(frame_bounds.XMax)) <= tolerance
        or abs(float(bounds.YMin) - float(frame_bounds.YMin)) <= tolerance
        or abs(float(bounds.YMax) - float(frame_bounds.YMax)) <= tolerance
    )


def _barrier_debug_shape(wall_footprint, auxiliary_entries):
    shapes = [wall_footprint.copy()]
    shapes.extend(entry["shape"].copy() for entry in list(auxiliary_entries or []))
    if len(shapes) == 1:
        return shapes[0]
    try:
        return Part.makeCompound(shapes)
    except Exception:
        return shapes[0]


def _topology_barrier_tools(wall_footprint, auxiliary_entries):
    """Return individual planar barrier faces for one fuzzy boolean operation.

    Keeping the wall faces as separate boolean tools is intentional: a T-junction
    can be visually closed while an exact sequential cut still leaves a weak
    topological connection at a coincident endpoint. OpenCASCADE's fuzzy boolean
    tolerance is applied only to this analysis operation; source BIM geometry and
    the DEBUG barrier reference remain unchanged.
    """
    tools = [face.copy() for face in list(getattr(wall_footprint, "Faces", []) or [])]
    for entry in list(auxiliary_entries or []):
        shape = entry["shape"]
        faces = list(getattr(shape, "Faces", []) or [])
        if faces:
            tools.extend(face.copy() for face in faces)
        elif shape is not None and not shape.isNull():
            tools.append(shape.copy())
    return tools


def room_faces_from_free_space(wall_footprint, auxiliary_entries, minimum_area_m2):
    """Detect rooms as connected free-space regions enclosed by BIM barriers.

    A temporary frame surrounding the model is cut in a single boolean operation
    by the individual wall/auxiliary faces. A small fuzzy tolerance seals
    T-junctions and near-coincident contacts for topology only, without modifying
    the source walls, columns or the exact DEBUG barrier geometry.
    """
    minimum_area = float(minimum_area_m2) * 1000000.0
    barrier_reference = _barrier_debug_shape(wall_footprint, auxiliary_entries)
    frame, margin = _analysis_frame(barrier_reference)
    barrier_tools = _topology_barrier_tools(wall_footprint, auxiliary_entries)
    if not barrier_tools:
        raise RuntimeError("No hay caras de barrera validas para el analisis topologico.")

    topology_tolerance = max(float(TOPOLOGY_FUZZY_TOLERANCE_MM), 0.0)
    try:
        free_space = frame.cut(barrier_tools, topology_tolerance)
        topology_mode = "fuzzy_cut"
    except Exception as exc:
        warn(
            "Cut topologico con tolerancia %.3f mm fallo (%s); se usa corte exacto secuencial."
            % (topology_tolerance, exc)
        )
        topology_mode = "exact_fallback"
        try:
            free_space = frame.copy()
            for tool in barrier_tools:
                free_space = free_space.cut(tool)
        except Exception as fallback_exc:
            raise RuntimeError(
                "No se pudo sustraer las barreras del marco de analisis: %s"
                % fallback_exc
            )

    try:
        free_space = free_space.removeSplitter()
    except Exception:
        pass
    if free_space is None or free_space.isNull() or not list(getattr(free_space, "Faces", []) or []):
        raise RuntimeError("El calculo de espacio libre no produjo caras planas validas.")

    rooms = []
    exterior_faces = []
    rejected_small = []
    seen = set()
    for face in list(free_space.Faces):
        if not face.isValid():
            continue
        if _face_touches_frame_boundary(face, frame):
            exterior_faces.append(face)
            continue
        if float(face.Area) < minimum_area:
            rejected_small.append(face)
            continue
        center = face.CenterOfMass
        key = (
            int(round(float(center.x) * 10.0)),
            int(round(float(center.y) * 10.0)),
            int(round(float(face.Area))),
        )
        if key in seen:
            continue
        seen.add(key)
        rooms.append(face)

    rooms.sort(key=lambda face: (-float(face.CenterOfMass.y), float(face.CenterOfMass.x)))
    log(
        "Espacio libre conectado: caras_libres=%d | exteriores=%d | recintos=%d | "
        "menores_minimo=%d | margen=%.1f mm | topologia=%s | tolerancia=%.3f mm | barreras=%d"
        % (
            len(list(free_space.Faces)),
            len(exterior_faces),
            len(rooms),
            len(rejected_small),
            margin,
            topology_mode,
            topology_tolerance,
            len(barrier_tools),
        )
    )
    return rooms, {
        "frame": frame,
        "barriers": barrier_reference,
        "free_space": free_space,
        "exterior_faces": exterior_faces,
        "room_faces": rooms,
        "rejected_small": rejected_small,
        "margin": margin,
        "topology_mode": topology_mode,
        "topology_tolerance_mm": topology_tolerance,
        "barrier_tool_count": len(barrier_tools),
    }


def room_faces_from_footprint(footprint, minimum_area_m2):
    """Legacy helper retained for compatibility; v1.3.x no longer uses it."""
    minimum_area = float(minimum_area_m2) * 1000000.0
    rooms = []
    seen = set()
    for wall_face in footprint.Faces:
        outer = wall_face.OuterWire
        for wire in wall_face.Wires:
            if same_wire(wire, outer):
                continue
            try:
                room = Part.Face(wire)
            except Exception as exc:
                warn("Contorno interior omitido: %s" % exc)
                continue
            if not room.isValid() or float(room.Area) < minimum_area:
                continue
            center = room.CenterOfMass
            key = (
                int(round(float(center.x) * 10.0)),
                int(round(float(center.y) * 10.0)),
                int(round(float(room.Area))),
            )
            if key in seen:
                continue
            seen.add(key)
            rooms.append(room)
    rooms.sort(key=lambda face: (-float(face.CenterOfMass.y), float(face.CenterOfMass.x)))
    return rooms


def suspicious_room_candidates(room_faces):
    """Find isolated huge room candidates without rejecting legitimate large rooms."""
    ranked = sorted(
        [(float(face.Area), face) for face in list(room_faces or [])],
        key=lambda item: item[0],
        reverse=True,
    )
    if len(ranked) < 3:
        return []
    largest_area, largest_face = ranked[0]
    second_area = ranked[1][0]
    minimum_area = float(SUSPICIOUS_ROOM_MIN_AREA_M2) * 1000000.0
    if largest_area < minimum_area or second_area <= 0.0:
        return []
    ratio = largest_area / second_area
    if ratio < float(SUSPICIOUS_ROOM_RATIO):
        return []
    return [(largest_face, largest_area, second_area, ratio)]


def text_lines(obj):
    if not hasattr(obj, "Text"):
        return []
    try:
        value = obj.Text
    except Exception:
        return []
    if isinstance(value, (list, tuple)):
        lines = [str(item).strip() for item in value]
    else:
        lines = [line.strip() for line in str(value).replace("\r", "\n").split("\n")]
    return [line for line in lines if line]


def clean_room_name(value):
    name = " ".join(str(value or "").strip().split())
    name = re.sub(r"(?<=\D)00\d$", "", name).strip()
    return name


def object_point(obj):
    try:
        point = obj.getGlobalPlacement().Base
        return float(point.x), float(point.y)
    except Exception:
        pass
    try:
        point = obj.Placement.Base
        return float(point.x), float(point.y)
    except Exception:
        return None


def shape_center(obj):
    try:
        shape = obj.Shape
        if shape.Faces:
            center = shape.CenterOfMass
            return float(center.x), float(center.y)
        bounds = shape.BoundBox
        return (float(bounds.XMin + bounds.XMax) * 0.5, float(bounds.YMin + bounds.YMax) * 0.5)
    except Exception:
        return None


def collect_name_candidates(doc, level=None):
    candidates = []
    seen = set()

    def allowed(obj):
        if level is None:
            return True
        stored = str(getattr(obj, "FA_LevelName", "") or "")
        if stored and stored != str(level.Name):
            return False
        native = object_native_levels(doc, obj)
        if native and level not in native:
            return False
        return True

    for obj in list(getattr(doc, "Objects", []) or []):
        if not allowed(obj):
            continue
        lines = text_lines(obj)
        label = object_label(obj)
        type_id = str(getattr(obj, "TypeId", "") or "").lower()
        if lines and ("text" in type_id or label.lower().startswith(("etiqueta", "rotulo", "rótulo"))):
            name = clean_room_name(lines[0])
            point = object_point(obj)
            if name and point and len(name) <= 120 and not re.match(r"^[\d.,+-]+$", name):
                key = (name.upper(), round(point[0], 1), round(point[1], 1))
                if key not in seen:
                    seen.add(key)
                    candidates.append({"name": name, "x": point[0], "y": point[1], "priority": 0})

    for obj in list(getattr(doc, "Objects", []) or []):
        if not allowed(obj):
            continue
        generated = str(getattr(obj, "FA_GeneratedBy", "") or "")
        role = str(getattr(obj, "FA_Role", "") or "").lower()
        electric_type = str(getattr(obj, "ElectricCRTipo", "") or "").lower()
        if generated == MACRO_ID:
            continue
        if generated != "FA_RectangularAreaAnalysis" and role not in ("room", "area", "room_area") and electric_type != "area":
            continue
        point = shape_center(obj)
        if point is None:
            continue
        name = ""
        for prop in ("FA_RoomName", "RoomName", "NombreRecinto"):
            name = clean_room_name(getattr(obj, prop, ""))
            if name:
                break
        name = name or clean_room_name(object_label(obj))
        if not name or name.lower().startswith(("area_", "rectangle", "wire")):
            continue
        key = (name.upper(), round(point[0], 1), round(point[1], 1))
        if key not in seen:
            seen.add(key)
            candidates.append({"name": name, "x": point[0], "y": point[1], "priority": 1})
    return candidates


def candidates_inside(face, candidates):
    result = []
    center = face.CenterOfMass
    for candidate in candidates:
        point = App.Vector(float(candidate["x"]), float(candidate["y"]), float(face.BoundBox.ZMin))
        try:
            inside = face.isInside(point, GEOMETRY_TOLERANCE_MM, True)
        except Exception:
            inside = False
        if inside:
            item = dict(candidate)
            item["distance"] = math.hypot(float(center.x) - item["x"], float(center.y) - item["y"])
            result.append(item)
    result.sort(key=lambda item: (item["priority"], item["distance"], item["name"]))
    return result


def ensure_group(doc, level=None):
    root = doc.getObject(GROUP_NAME)
    if root is None:
        root = doc.addObject("App::DocumentObjectGroup", GROUP_NAME)
    root.Label = GROUP_LABEL
    parent = doc.getObject("FA_Areas")
    if parent is None:
        for obj in doc.Objects:
            if object_label(obj).strip().lower() in ("04_areas", "areas"):
                parent = obj
                break
    if parent is not None:
        try:
            if root not in list(getattr(parent, "Group", []) or []):
                parent.addObject(root)
        except Exception:
            pass
    if level is None:
        return root

    name = LEVEL_GROUP_NAME_PREFIX + str(level.Name)
    group = doc.getObject(name)
    if group is None:
        group = doc.addObject("App::DocumentObjectGroup", name)
    group.Label = "Recintos - %s" % object_label(level)
    set_property(group, "App::PropertyString", "FA_GeneratedBy", "FacilArquitectura", "Macro generadora", MACRO_ID)
    set_property(group, "App::PropertyString", "FA_Role", "FacilArquitectura", "Rol", "room_polygon_level_group")
    tag_level_metadata(group, level)
    try:
        if group not in list(getattr(root, "Group", []) or []):
            root.addObject(group)
    except Exception:
        pass
    return group


def _generated_object_level(doc, obj):
    """Resolve level identity for current and legacy generated outputs."""
    name = str(getattr(obj, "FA_LevelName", "") or "")
    if name:
        return doc.getObject(name)
    source_walls = list(getattr(obj, "FA_SourceWalls", []) or [])
    levels = []
    for wall in source_walls:
        levels.extend(object_native_levels(doc, wall))
    levels = unique_objects(levels)
    if len(levels) == 1:
        return levels[0]
    owner_name = str(getattr(obj, "FA_OwnerName", "") or "")
    if owner_name:
        owner = doc.getObject(owner_name)
        if owner is not None and owner is not obj:
            return _generated_object_level(doc, owner)
    return None


def remove_previous_outputs(doc, level):
    """Replace outputs only for the current storey; preserve every other floor."""
    removed = 0
    current_name = str(level.Name)
    candidates = []
    for obj in list(doc.Objects):
        if str(getattr(obj, "FA_GeneratedBy", "") or "") != MACRO_ID:
            continue
        if str(getattr(obj, "Name", "") or "") == GROUP_NAME:
            continue
        role = str(getattr(obj, "FA_Role", "") or "")
        if role == "room_polygon_level_group":
            continue
        resolved = _generated_object_level(doc, obj)
        if resolved is level or str(getattr(obj, "FA_LevelName", "") or "") == current_name:
            candidates.append(obj)
            continue
        # Legacy diagnostics and the single pre-v1.4 schedule are not level-safe.
        # They contain no architectural result that should survive migration.
        if resolved is None and (role.startswith("debug_") or role == "room_polygon_schedule"):
            candidates.append(obj)

    # Remove boundaries/diagnostics before owning room objects when possible.
    candidates.sort(key=lambda obj: 0 if str(getattr(obj, "FA_Role", "") or "") in ("room_polygon_boundary",) else 1)
    for obj in candidates:
        try:
            if doc.getObject(obj.Name) is not None:
                doc.removeObject(obj.Name)
                removed += 1
        except Exception as exc:
            warn("No se pudo reemplazar %s: %s" % (object_label(obj), exc))
    return removed


def unique_label(doc, base):
    existing = {object_label(obj) for obj in doc.Objects}
    if base not in existing:
        return base
    index = 2
    while "%s %02d" % (base, index) in existing:
        index += 1
    return "%s %02d" % (base, index)


def ordered_outer_wire_points(room_face):
    """Return ordered local points from a planar face without a closing duplicate."""
    try:
        vertices = list(room_face.OuterWire.OrderedVertexes)
    except Exception as exc:
        raise RuntimeError("No se pudo ordenar el contorno interior: %s" % exc)
    if len(vertices) < 3:
        raise RuntimeError("El contorno interior tiene menos de tres vertices.")

    source_z = float(room_face.BoundBox.ZMin)
    points = []
    for vertex in vertices:
        point = vertex.Point
        local = App.Vector(float(point.x), float(point.y), float(point.z) - source_z)
        if points and local.isEqual(points[-1], GEOMETRY_TOLERANCE_MM):
            continue
        points.append(local)

    if len(points) > 1 and points[0].isEqual(points[-1], GEOMETRY_TOLERANCE_MM):
        points.pop()
    if len(points) < 3:
        raise RuntimeError("El contorno interior valido tiene menos de tres puntos distintos.")
    if any(abs(float(point.z)) > GEOMETRY_TOLERANCE_MM for point in points):
        raise RuntimeError("El contorno interior no es plano en Z.")
    return points, source_z


def make_editable_room_wire(doc, room_face, display_z_mm=None):
    """Create the native Draft Wire used as editable room geometry."""
    if App.ActiveDocument is not doc:
        raise RuntimeError("El documento destino debe estar activo para crear el Draft Wire.")
    points, source_z = ordered_outer_wire_points(room_face)
    maker = getattr(Draft, "make_wire", None) or getattr(Draft, "makeWire", None)
    if maker is None:
        raise RuntimeError("Draft.make_wire no esta disponible en esta instalacion de FreeCAD.")
    obj = maker(points, closed=True, face=True)
    if obj is None:
        raise RuntimeError("Draft.make_wire no pudo crear el recinto poligonal.")
    if getattr(obj, "Document", None) is not doc:
        raise RuntimeError("Draft.make_wire creo el objeto en un documento distinto al esperado.")
    obj.Closed = True
    obj.MakeFace = True
    target_z = source_z + DISPLAY_ELEVATION_MM if display_z_mm is None else float(display_z_mm)
    obj.Placement = App.Placement(App.Vector(0.0, 0.0, target_z), App.Rotation())
    return obj, points


def obstacle_sources_for_room(room_face, obstacle_entries):
    """Associate isolated auxiliary footprints with a free-space room face."""
    result = []
    seen = set()
    try:
        gross_face = Part.Face(room_face.OuterWire)
    except Exception:
        gross_face = None
    for entry in list(obstacle_entries or []):
        footprint = entry["shape"]
        applies = False
        if gross_face is not None:
            try:
                overlap = gross_face.common(footprint)
                applies = shape_area(overlap) > max(
                    GEOMETRY_TOLERANCE_MM * GEOMETRY_TOLERANCE_MM, 0.01
                )
            except Exception:
                applies = False
        if not applies:
            continue
        obj = entry["object"]
        name = str(getattr(obj, "Name", "") or id(obj))
        if name in seen:
            continue
        seen.add(name)
        result.append(obj)
    return result


def ensure_debug_group(doc, parent_group, level):
    name = DEBUG_GROUP_NAME_PREFIX + str(level.Name)
    group = doc.getObject(name)
    if group is None:
        group = doc.addObject("App::DocumentObjectGroup", name)
    group.Label = "%s - %s" % (DEBUG_GROUP_LABEL_PREFIX, object_label(level))
    set_property(group, "App::PropertyString", "FA_GeneratedBy", "FacilArquitectura", "Macro generadora", MACRO_ID)
    set_property(group, "App::PropertyString", "FA_Role", "FacilArquitectura", "Rol diagnostico", "debug_group")
    tag_level_metadata(group, level)
    try:
        if group not in list(getattr(parent_group, "Group", []) or []):
            parent_group.addObject(group)
    except Exception:
        pass
    return group


def _debug_feature(doc, group, name, label, shape, role, level, display_z_mm):
    existing = doc.getObject(name)
    if existing is not None:
        try:
            doc.removeObject(existing.Name)
        except Exception:
            pass
    obj = doc.addObject("Part::Feature", name)
    obj.Label = label
    obj.Shape = shape.copy()
    obj.Placement = App.Placement(App.Vector(0.0, 0.0, float(display_z_mm)), App.Rotation())
    set_property(obj, "App::PropertyString", "FA_GeneratedBy", "FacilArquitectura", "Macro generadora", MACRO_ID)
    set_property(obj, "App::PropertyString", "FA_Role", "FacilArquitectura", "Rol diagnostico", role)
    set_property(obj, "App::PropertyBool", "DocumentationOnly", "FacilArquitectura", "Solo diagnostico", True)
    tag_level_metadata(obj, level)
    try:
        group.addObject(obj)
        obj.ViewObject.Visibility = False
        obj.ViewObject.Transparency = 80
        obj.ViewObject.LineWidth = 2.0
    except Exception:
        pass
    return obj


def create_debug_geometry(doc, parent_group, topology, level):
    """Create hidden read-only diagnostic geometry scoped to one storey."""
    if not DEBUG_GEOMETRY:
        return []
    group = ensure_debug_group(doc, parent_group, level)
    created = []
    suffix = "_" + str(level.Name)
    display_z = level_elevation_mm(level) + DISPLAY_ELEVATION_MM * 0.25
    barriers = topology.get("barriers")
    if barriers is not None and not barriers.isNull():
        created.append(
            _debug_feature(doc, group, "DEBUG_Barreras" + suffix, "DEBUG - Barreras 2D - " + object_label(level), barriers, "debug_barriers", level, display_z)
        )
    exterior_faces = list(topology.get("exterior_faces") or [])
    if exterior_faces:
        exterior = Part.makeCompound([face.copy() for face in exterior_faces])
        created.append(
            _debug_feature(doc, group, "DEBUG_Exterior" + suffix, "DEBUG - Espacio exterior - " + object_label(level), exterior, "debug_exterior", level, display_z)
        )
    room_faces = list(topology.get("room_faces") or [])
    if room_faces:
        candidates = Part.makeCompound([face.copy() for face in room_faces])
        created.append(
            _debug_feature(doc, group, "DEBUG_RecintosCandidatos" + suffix, "DEBUG - Recintos candidatos - " + object_label(level), candidates, "debug_room_candidates", level, display_z)
        )
    log("Geometria DEBUG creada: %d objetos | nivel=%s (ocultos por defecto)." % (len(created), object_label(level)))
    return created


def create_room_object(
    doc,
    group,
    room_face,
    walls,
    name_candidates,
    index,
    obstacle_entries=None,
    closure_entries=None,
    precut=False,
    level=None,
):
    obstacle_entries = list(obstacle_entries or [])
    closure_entries = list(closure_entries or [])
    display_z = level_elevation_mm(level) + DISPLAY_ELEVATION_MM if level is not None else DISPLAY_ELEVATION_MM
    if precut:
        net_shape = room_face.copy()
        try:
            gross_face = Part.Face(room_face.OuterWire)
            gross_area = float(gross_face.Area)
        except Exception:
            gross_area = float(room_face.Area)
        net_area = shape_area(net_shape)
        removed_area = max(0.0, gross_area - net_area)
        used_obstacles = obstacle_sources_for_room(room_face, obstacle_entries)
    else:
        net_shape, used_obstacles, removed_area = subtract_obstacles(room_face, obstacle_entries)
        gross_area = float(room_face.Area)
        net_area = shape_area(net_shape)
    used_closures = closure_sources_for_room(room_face, closure_entries)
    matches = candidates_inside(room_face, name_candidates)
    room_name = matches[0]["name"] if matches else "Recinto poligonal %02d" % index
    boundary = None
    has_holes = len(list(getattr(room_face, "Wires", []) or [])) > 1

    if used_obstacles or (precut and has_holes):
        boundary, points = make_editable_room_wire(doc, room_face, display_z_mm=display_z)
        boundary.Label = unique_label(doc, "Contorno editable - " + room_name)
        boundary.MakeFace = False
        set_property(boundary, "App::PropertyString", "FA_GeneratedBy", "FacilArquitectura", "Macro generadora", MACRO_ID)
        set_property(boundary, "App::PropertyString", "FA_Role", "FacilArquitectura", "Rol", "room_polygon_boundary")
        tag_level_metadata(boundary, level)
        try:
            boundary.ViewObject.LineColor = (0.95, 0.45, 0.05)
            boundary.ViewObject.LineWidth = 2.0
        except Exception:
            pass

        obj = doc.addObject("Part::Feature", "FA_PolygonalRoom")
        display_shape = net_shape.copy()
        display_shape.translate(App.Vector(0.0, 0.0, display_z))
        obj.Shape = display_shape
        geometry_type = "PartFaceWithHoles"
        source_method = (
            "Espacio libre conectado multinivel: huella nominal de muros + auxiliares"
            if precut
            else "Huecos de huella BIM con cierres seleccionados menos obstaculos interiores"
        )
        set_property(obj, "App::PropertyLink", "FA_EditBoundary", "FacilArquitectura", "Contorno exterior Draft editable", boundary)
        set_property(boundary, "App::PropertyString", "FA_OwnerName", "FacilArquitectura", "Nombre interno del recinto neto asociado", str(getattr(obj, "Name", "") or ""))
        vertex_count = len(list(getattr(net_shape, "Vertexes", []) or []))
    else:
        obj, points = make_editable_room_wire(doc, room_face, display_z_mm=display_z)
        geometry_type = "DraftWire"
        source_method = (
            "Espacio libre conectado multinivel: huella nominal de muros + auxiliares"
            if precut
            else (
                "Huecos de huella BIM con elementos de cierre seleccionados"
                if used_closures
                else "Huecos de huella superior Arch Wall"
            )
        )
        vertex_count = len(points)

    obj.Label = unique_label(doc, "Poligono - " + room_name)
    perimeter = shape_perimeter(net_shape) if (used_obstacles or (precut and has_holes)) else float(room_face.OuterWire.Length)
    set_property(obj, "App::PropertyString", "ElectricCRTipo", "ElectricCR", "Tipo logico", "Area")
    set_property(obj, "App::PropertyString", "GeneratedBy", "ElectricCR", "Macro generadora", MACRO_ID)
    set_property(obj, "App::PropertyFloat", "AreaM2", "ElectricCR", "Area neta del recinto", net_area / 1000000.0)
    set_property(obj, "App::PropertyInteger", "VirtualClosures", "ElectricCR", "Cierres virtuales", 0)
    set_property(obj, "App::PropertyFloat", "Confidence", "ElectricCR", "Confianza geometrica", 1.0)
    set_property(obj, "App::PropertyString", "FA_GeneratedBy", "FacilArquitectura", "Macro generadora", MACRO_ID)
    set_property(obj, "App::PropertyString", "FA_Role", "FacilArquitectura", "Rol", "room_polygon")
    tag_level_metadata(obj, level)
    set_property(obj, "App::PropertyString", "FA_RoomName", "FacilArquitectura", "Nombre del recinto", room_name)
    set_property(obj, "App::PropertyArea", "FA_Area", "FacilArquitectura", "Area neta exacta", net_area)
    set_property(obj, "App::PropertyArea", "FA_GrossArea", "FacilArquitectura", "Area bruta antes de obstaculos", gross_area)
    set_property(obj, "App::PropertyArea", "FA_ObstacleArea", "FacilArquitectura", "Area descontada por obstaculos", removed_area)
    set_property(obj, "App::PropertyArea", "FA_NetArea", "FacilArquitectura", "Area neta util", net_area)
    set_property(obj, "App::PropertyLength", "FA_Perimeter", "FacilArquitectura", "Perimetro neto", perimeter)
    set_property(obj, "App::PropertyInteger", "FA_VertexCount", "FacilArquitectura", "Vertices de la geometria", vertex_count)
    set_property(obj, "App::PropertyInteger", "FA_NameCandidateCount", "FacilArquitectura", "Rotulos dentro del recinto", len(matches))
    set_property(obj, "App::PropertyStringList", "FA_NameCandidates", "FacilArquitectura", "Nombres candidatos", [item["name"] for item in matches])
    set_property(obj, "App::PropertyLinkList", "FA_SourceWalls", "FacilArquitectura", "Muros fuente", list(walls))
    set_property(obj, "App::PropertyLinkList", "FA_SourceClosures", "FacilArquitectura", "Elementos seleccionados que cierran el recinto", list(used_closures))
    set_property(obj, "App::PropertyInteger", "FA_ClosureCount", "FacilArquitectura", "Cantidad de objetos de cierre asociados", len(used_closures))
    set_property(obj, "App::PropertyLinkList", "FA_SourceObstacles", "FacilArquitectura", "Obstaculos interiores descontados", list(used_obstacles))
    set_property(obj, "App::PropertyInteger", "FA_ObstacleCount", "FacilArquitectura", "Cantidad de obstaculos interiores descontados", len(used_obstacles))
    set_property(obj, "App::PropertyString", "FA_SourceMethod", "FacilArquitectura", "Metodo geometrico", source_method)
    set_property(obj, "App::PropertyString", "FA_UsableFor", "FacilArquitectura", "Flujos consumidores", "HVAC; sensores de humo; cielo suspendido; ElectricCR")
    set_property(obj, "App::PropertyString", "FA_GeometrySource", "FacilArquitectura", "Origen de la geometria", "AUTO_BIM")
    set_property(obj, "App::PropertyString", "FA_GeometryType", "FacilArquitectura", "Tipo de geometria editable", geometry_type)
    try:
        if boundary is not None:
            group.addObject(boundary)
        group.addObject(obj)
        obj.ViewObject.LineColor = (0.85, 0.30, 0.00)
        obj.ViewObject.ShapeColor = (1.00, 0.65, 0.15)
        obj.ViewObject.Transparency = 75
        obj.ViewObject.LineWidth = 2.0
    except Exception:
        pass
    log(
        "Creado %s: nivel=%s | geometria=%s | area_bruta=%.3f m2 | area_neta=%.3f m2 | cierres=%d | obstaculos=%d | Z=%.3f"
        % (
            obj.Name,
            object_label(level) if level is not None else "<sin nivel>",
            geometry_type,
            gross_area / 1000000.0,
            net_area / 1000000.0,
            len(used_closures),
            len(used_obstacles),
            display_z,
        )
    )
    return obj, matches


def column_name(index):
    result = ""
    while index:
        index, remainder = divmod(index - 1, 26)
        result = chr(65 + remainder) + result
    return result


def write_schedule(doc, group, room_objects, level):
    sheet_name = SHEET_NAME_PREFIX + str(level.Name)
    sheet = doc.getObject(sheet_name)
    if sheet is None:
        sheet = doc.addObject("Spreadsheet::Sheet", sheet_name)
    sheet.Label = "Cuadro de recintos - %s" % object_label(level)
    try:
        sheet.clearAll()
    except Exception:
        pass
    headers = (
        "Recinto",
        "Nivel",
        "Elevacion_mm",
        "Area_m2",
        "Perimetro_m",
        "Vertices",
        "Rotulos_encontrados",
        "Muros_fuente",
        "Elementos_cierre",
        "Obstaculos_interiores",
        "Area_bruta_m2",
        "Area_obstaculos_m2",
        "Geometria",
    )
    for column, value in enumerate(headers, 1):
        cell = column_name(column) + "1"
        sheet.set(cell, value)
        try:
            sheet.setStyle(cell, "bold", "add")
        except Exception:
            pass
    elevation = level_elevation_mm(level)
    for row, obj in enumerate(room_objects, 2):
        closures = list(getattr(obj, "FA_SourceClosures", []) or [])
        obstacles = list(getattr(obj, "FA_SourceObstacles", []) or [])
        gross_area = float(getattr(getattr(obj, "FA_GrossArea", 0.0), "Value", getattr(obj, "FA_GrossArea", 0.0)))
        obstacle_area = float(getattr(getattr(obj, "FA_ObstacleArea", 0.0), "Value", getattr(obj, "FA_ObstacleArea", 0.0)))
        values = (
            str(getattr(obj, "FA_RoomName", obj.Label)),
            object_label(level),
            "%.3f" % elevation,
            "%.3f" % float(obj.AreaM2),
            "%.3f" % (float(obj.FA_Perimeter.Value) / 1000.0),
            str(int(obj.FA_VertexCount)),
            str(int(obj.FA_NameCandidateCount)),
            ", ".join(object_label(wall) for wall in list(obj.FA_SourceWalls or [])),
            ", ".join(object_label(item) for item in closures),
            ", ".join(object_label(item) for item in obstacles),
            "%.3f" % (gross_area / 1000000.0),
            "%.3f" % (obstacle_area / 1000000.0),
            str(getattr(obj, "FA_GeometryType", "")),
        )
        for column, value in enumerate(values, 1):
            sheet.set(column_name(column) + str(row), str(value))
    widths = (220, 120, 100, 90, 100, 75, 125, 260, 220, 220, 105, 125, 145)
    for column, width in enumerate(widths, 1):
        try:
            sheet.setColumnWidth(column_name(column), width)
        except Exception:
            pass
    set_property(sheet, "App::PropertyString", "FA_GeneratedBy", "FacilArquitectura", "Macro generadora", MACRO_ID)
    set_property(sheet, "App::PropertyString", "FA_Role", "FacilArquitectura", "Rol", "room_polygon_schedule")
    tag_level_metadata(sheet, level)
    try:
        group.addObject(sheet)
    except Exception:
        pass
    return sheet


def generate_polygonal_rooms(doc=None, walls=None, obstacles=None, minimum_area_m2=MIN_ROOM_AREA_M2, level=None):
    doc = doc or App.ActiveDocument
    if doc is None:
        raise RuntimeError("No hay documento activo.")

    selected_mode = False
    source_mode = "parametros"
    if walls is None:
        walls, selected_obstacles, selected_mode, source_mode, level = collect_sources(doc, level=level)
        if obstacles is None:
            obstacles = selected_obstacles
    else:
        level = resolve_analysis_level(doc, walls_hint=walls, explicit_level=level)
        if obstacles is None:
            _auto_walls, obstacles, selected_mode, source_mode, _resolved = collect_sources(doc, level=level, walls_hint=walls)

    walls = unique_objects([wall for wall in list(walls or []) if is_arch_wall(wall)])
    obstacles = unique_objects([obj for obj in list(obstacles or []) if is_selected_obstacle(obj, explicitly_selected=True)])
    if not walls:
        raise RuntimeError("El nivel no contiene muros Arch/BIM validos.")

    elevation = level_elevation_mm(level)
    wall_footprint, source_face_count = fuse_wall_footprints(walls)
    auxiliary_entries, obstacle_face_count = obstacle_footprints(obstacles)
    if obstacles and not auxiliary_entries:
        warn("Se detectaron %d auxiliares, pero ninguno produjo una huella horizontal valida." % len(obstacles))

    closure_entries, interior_entries = classify_auxiliary_components(wall_footprint, auxiliary_entries)
    closure_diagnostic_footprint = fuse_closure_footprints(wall_footprint, closure_entries)
    room_faces, topology = room_faces_from_free_space(wall_footprint, auxiliary_entries, minimum_area_m2)
    footprint = topology["barriers"]
    if not room_faces:
        raise RuntimeError(
            "El analisis de espacio libre no encontro recintos encerrados en '%s'. "
            "Revise continuidad de muros/columnas y la geometria DEBUG del nivel."
            % object_label(level)
        )

    if auxiliary_entries:
        applied_closures = [entry for entry in closure_entries if entry.get("closure_applied", False)]
        contributing_closures = [
            entry for entry in applied_closures
            if float(entry.get("closure_added_area", 0.0) or 0.0) > 0.01
        ]
        log(
            "Clasificacion auxiliar: componentes=%d | componentes_cierre=%d | cierres_aplicados=%d | cierres_con_aporte=%d | componentes_interiores=%d"
            % (len(auxiliary_entries), len(closure_entries), len(applied_closures), len(contributing_closures), len(interior_entries))
        )

    suspicious = suspicious_room_candidates(room_faces)
    for _face, largest_area, second_area, ratio in suspicious:
        warn(
            "Recinto candidato anormalmente grande: %.3f m2 | segundo mayor=%.3f m2 | relacion=%.1fx. "
            "No se descarta automaticamente; revise si requiere una division funcional manual."
            % (largest_area / 1000000.0, second_area / 1000000.0, ratio)
        )

    name_candidates = collect_name_candidates(doc, level=level)
    doc.openTransaction("FA crear recintos poligonales - %s" % object_label(level))
    try:
        removed = remove_previous_outputs(doc, level)
        group = ensure_group(doc, level)
        debug_objects = create_debug_geometry(doc, group, topology, level)
        created = []
        ambiguous = []
        unnamed = []
        for index, room_face in enumerate(room_faces, 1):
            obj, matches = create_room_object(
                doc,
                group,
                room_face,
                walls,
                name_candidates,
                index,
                obstacle_entries=interior_entries,
                closure_entries=closure_entries,
                precut=True,
                level=level,
            )
            created.append(obj)
            if not matches:
                unnamed.append(obj)
            elif len({item["name"].upper() for item in matches}) > 1:
                ambiguous.append(obj)
        sheet = write_schedule(doc, group, created, level)
        doc.recompute()

        invalid = []
        for obj in created:
            faces = list(getattr(getattr(obj, "Shape", None), "Faces", []) or [])
            geometry_type = str(getattr(obj, "FA_GeometryType", "") or "")
            if not faces:
                invalid.append(obj)
                continue
            if geometry_type == "DraftWire":
                if not bool(getattr(obj, "Closed", False)) or not bool(getattr(obj, "MakeFace", False)):
                    invalid.append(obj)
        if invalid:
            raise RuntimeError(
                "Los siguientes recintos no generaron una cara valida: %s"
                % ", ".join(object_label(obj) for obj in invalid)
            )
        doc.commitTransaction()
    except Exception:
        try:
            doc.abortTransaction()
        except Exception:
            pass
        raise

    used_closures = unique_objects(
        [
            entry["object"] for entry in closure_entries
            if entry.get("closure_applied", False)
            and float(entry.get("closure_added_area", 0.0) or 0.0) > 0.01
        ]
    )
    used_obstacles = unique_objects(
        [obstacle for obj in created for obstacle in list(getattr(obj, "FA_SourceObstacles", []) or [])]
    )
    log(
        "Completado: nivel=%s [%s] | elevacion=%.3f mm | recintos=%d | muros=%d | auxiliares=%d | "
        "componentes_cierre=%d | objetos_cierre_usados=%d | obstaculos_interiores_usados=%d | "
        "caras_muro=%d | caras_auxiliares=%d | reemplazados_nivel=%d | sin_rotulo=%d | ambiguos=%d | "
        "metodo=espacio_libre_multinivel | origen=%s"
        % (
            object_label(level), level.Name, elevation, len(created), len(walls), len(obstacles),
            len(closure_entries), len(used_closures), len(used_obstacles), source_face_count,
            obstacle_face_count, removed, len(unnamed), len(ambiguous), source_mode,
        )
    )
    if ambiguous:
        warn("Hay %d poligonos con varios rotulos distintos en %s." % (len(ambiguous), object_label(level)))
    return {
        "level": level,
        "walls": walls,
        "obstacles": obstacles,
        "closure_entries": closure_entries,
        "interior_entries": interior_entries,
        "used_closures": used_closures,
        "used_obstacles": used_obstacles,
        "footprint": footprint,
        "topology": topology,
        "debug_objects": debug_objects,
        "rooms": created,
        "sheet": sheet,
        "unnamed": unnamed,
        "ambiguous": ambiguous,
    }


def main():
    macro_path = str(globals().get("__file__", "<FreeCAD macro>"))
    log("Inicio | version=%s | archivo=%s" % (MACRO_VERSION, macro_path))
    try:
        return generate_polygonal_rooms()
    except Exception as exc:
        error(str(exc))
        return None


FA_POLYGONAL_ROOMS_RESULT = main()

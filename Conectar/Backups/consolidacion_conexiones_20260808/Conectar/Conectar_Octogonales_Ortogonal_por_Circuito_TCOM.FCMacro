# -*- coding: utf-8 -*-
# MenuText: Conectar Octogonales Ortogonal por Circuito TCOM...
# Icon: Conectar/Conectar_Octogonales_Ortogonal_por_Circuito_TCOM.svg

"""Backbone EMT ortogonal para TCOM-01..TCOM-05, separado de la red TP."""

from pathlib import Path
import json
import re

import FreeCAD as App


TAG = "[OCTO_ORTO_TCOM]"
GENERATED_BY = "Conectar_Octogonales_Ortogonal_por_Circuito_TCOM"
FEEDER_GENERATOR = "Conectar_Circuitos_TCOM_a_Cara_Superior_Tablero"
TP_BACKBONE_MACRO = "Conectar_Octogonales_Ortogonal_por_Circuito_TP.FCMacro"
TCOM_FEEDER_MACRO = "Conectar_Circuitos_TCOM_a_Cara_Superior_Tablero.FCMacro"
PARAM_PATH = "User parameter:BaseApp/Preferences/Mod/ElectricCR/OctoOrtoTCOM"
DEFAULT_ROUTE_Z = 3400.0
DEFAULT_BEND_RADIUS = 100.0
DEFAULT_PORT_STUB = 80.0
DEFAULT_DIAMETER = 22.2


def _load_macro_definitions(filename, module_name):
    path = Path(__file__).resolve().with_name(filename)
    if not path.exists():
        raise RuntimeError("No se encontro la macro auxiliar: " + str(path))
    source = path.read_text(encoding="utf-8-sig")
    source = re.sub(
        r"\nif\s+__name__\s*==\s*[\"']__main__[\"']\s*:\s*\n\s*main\(\)\s*\Z",
        "\n",
        source,
        flags=re.MULTILINE,
    )
    namespace = {"__name__": module_name, "__file__": str(path)}
    exec(compile(source, str(path), "exec"), namespace, namespace)
    return namespace


_TP = _load_macro_definitions(TP_BACKBONE_MACRO, "_electriccr_tp_backbone_helpers_tcom")
_TCOM = _load_macro_definitions(TCOM_FEEDER_MACRO, "_electriccr_tcom_feeder_helpers_branch")
Gui = _TCOM.get("Gui")
GUI_UP = bool(_TCOM.get("GUI_UP", False))
QtWidgets = _TCOM.get("QtWidgets")


def _log(message):
    App.Console.PrintMessage(TAG + " " + str(message) + "\n")


def _warn(message):
    App.Console.PrintWarning(TAG + " " + str(message) + "\n")


def _err(message):
    App.Console.PrintError(TAG + " " + str(message) + "\n")


def _safe(value):
    try:
        return str(value or "")
    except Exception:
        return ""


def _ensure_property(obj, ptype, name, group, description):
    if name not in getattr(obj, "PropertiesList", []):
        obj.addProperty(ptype, name, group, description)


def _feeder_root(doc, circuit_id, boxes):
    for obj in doc.Objects:
        if not _safe(getattr(obj, "Name", "")).startswith("Alimentador_TCOM"):
            continue
        if _safe(getattr(obj, "GeneradoPor", "")) != FEEDER_GENERATOR:
            continue
        if _safe(getattr(obj, "CircuitoID", "")) != circuit_id:
            continue
        box = getattr(obj, "CajaOrigen", None)
        if box in boxes:
            return box
    return None


def _reserved_ports(doc, boxes):
    names = {box.Name for box in boxes}
    reserved = {name: set() for name in names}
    for obj in doc.Objects:
        object_name = _safe(getattr(obj, "Name", ""))
        if not object_name.startswith(("EMT_Conexion", "Alimentador_", "Ramal_")):
            continue
        if _safe(getattr(obj, "GeneradoPor", "")) == GENERATED_BY:
            continue
        properties = set(getattr(obj, "PropertiesList", []) or [])
        if "CajaDestino" in properties:
            box_name = _safe(getattr(obj, "CajaDestino", ""))
            port_name = _safe(getattr(obj, "PuertoDestino", ""))
            if box_name in reserved and port_name:
                reserved[box_name].add(port_name)
        if "CajaOrigen" in properties:
            box = getattr(obj, "CajaOrigen", None)
            port_name = _safe(getattr(obj, "PuertoOrigen", ""))
            if box is not None and getattr(box, "Name", "") in reserved and port_name:
                reserved[box.Name].add(port_name)
        if "CajaDestinoLink" in properties:
            box = getattr(obj, "CajaDestinoLink", None)
            port_name = _safe(getattr(obj, "PuertoDestino", ""))
            if box is not None and getattr(box, "Name", "") in reserved and port_name:
                reserved[box.Name].add(port_name)
    return reserved


def _key(circuit_id, source, destination):
    names = sorted((source.Name, destination.Name))
    return circuit_id + "|" + names[0] + "|" + names[1]


def _find_existing(doc, key):
    for obj in doc.Objects:
        if _safe(getattr(obj, "GeneradoPor", "")) == GENERATED_BY and _safe(getattr(obj, "ConexionKey", "")) == key:
            return obj
    return None


def _ensure_group(doc, circuit_group, circuit_id):
    label = "Ramales EMT " + circuit_id
    for child in list(getattr(circuit_group, "Group", []) or []):
        if hasattr(child, "Group") and _safe(getattr(child, "Label", "")) == label:
            return child
    name = _TP["_H"]["_unique_name"](doc, "Grupo_Ramales_EMT_" + circuit_id.replace("-", "_"))
    group = doc.addObject("App::DocumentObjectGroup", name)
    group.Label = label
    _ensure_property(group, "App::PropertyString", "GeneradoPor", "ElectricCR", "Generador")
    group.GeneradoPor = GENERATED_BY
    circuit_group.addObject(group)
    return group


def _move_to_group(obj, target):
    for parent in list(getattr(obj, "InList", []) or []):
        if parent is target or not hasattr(parent, "Group"):
            continue
        if _safe(getattr(parent, "GeneradoPor", "")) == GENERATED_BY:
            try:
                parent.removeObject(obj)
            except Exception:
                pass
    target.addObject(obj)


def _style(obj):
    try:
        color = (0.20, 0.90, 0.42)
        obj.ViewObject.LineColor = color
        obj.ViewObject.PointColor = color
        obj.ViewObject.ShapeColor = color
        obj.ViewObject.LineWidth = 3.0
    except Exception:
        pass


def _write_branch(doc, circuit_group, circuit_id, index, source, destination, source_data, destination_data, points, cfg):
    key = _key(circuit_id, source, destination)
    obj = _find_existing(doc, key)
    created = obj is None
    if obj is None:
        name = "Ramal_%s_%02d" % (circuit_id.replace("-", "_"), index)
        obj = doc.addObject("Part::Feature", _TP["_H"]["_unique_name"](doc, name))
    obj.Label = "Ramal %s: %s -> %s" % (circuit_id, source.Label, destination.Label)
    obj.Shape = _TP["_H"]["_rounded_wire"](points, float(cfg["bend_radius"]))
    properties = [
        ("App::PropertyString", "GeneradoPor", "ElectricCR", "Generador"),
        ("App::PropertyString", "CircuitoID", "ElectricCR", "Circuito"),
        ("App::PropertyString", "ConexionKey", "ElectricCR", "Clave"),
        ("App::PropertyString", "TipoConexion", "ElectricCR", "Tipo"),
        ("App::PropertyString", "ConduitType", "ElectricCR", "Tuberia"),
        ("App::PropertyFloat", "DiametroEMT", "ElectricCR", "Diametro"),
        ("App::PropertyLink", "CajaOrigen", "Vinculos", "Caja origen"),
        ("App::PropertyLink", "CajaDestinoLink", "Vinculos", "Caja destino"),
        ("App::PropertyString", "PuertoOrigen", "Puertos", "Puerto origen"),
        ("App::PropertyString", "PuertoDestino", "Puertos", "Puerto destino"),
        ("App::PropertyVector", "PuntoOrigen", "Puertos", "Inicio"),
        ("App::PropertyVector", "PuntoDestino", "Puertos", "Destino"),
        ("App::PropertyFloat", "AlturaRuta", "Ruta", "Cota"),
        ("App::PropertyString", "RutaJSON", "Ruta", "Puntos"),
        ("App::PropertyString", "EstadoConexion", "Ruta", "Estado"),
    ]
    for data in properties:
        _ensure_property(obj, *data)
    obj.GeneradoPor = GENERATED_BY
    obj.CircuitoID = circuit_id
    obj.ConexionKey = key
    obj.TipoConexion = "EMT_Ortogonal_Octogonal"
    obj.ConduitType = "EMT"
    obj.DiametroEMT = float(cfg["diameter"])
    obj.CajaOrigen = source
    obj.CajaDestinoLink = destination
    obj.PuertoOrigen = source_data[2]
    obj.PuertoDestino = destination_data[2]
    obj.PuntoOrigen = App.Vector(source_data[0])
    obj.PuntoDestino = App.Vector(destination_data[0])
    obj.AlturaRuta = float(cfg["route_z"])
    obj.RutaJSON = json.dumps([[p.x, p.y, p.z] for p in points], separators=(",", ":"))
    obj.EstadoConexion = "Conectado"
    _style(obj)
    _move_to_group(obj, _ensure_group(doc, circuit_group, circuit_id))
    return obj, created


def _delete_stale(doc, valid_keys):
    stale = [obj for obj in doc.Objects if _safe(getattr(obj, "GeneradoPor", "")) == GENERATED_BY and not hasattr(obj, "Group") and _safe(getattr(obj, "ConexionKey", "")) not in valid_keys]
    for obj in stale:
        doc.removeObject(obj.Name)
    return len(stale)


def _cleanup_empty_groups(doc):
    for group in list(doc.Objects):
        if hasattr(group, "Group") and _safe(getattr(group, "GeneradoPor", "")) == GENERATED_BY and not list(group.Group):
            doc.removeObject(group.Name)


def _default_cfg():
    p = App.ParamGet(PARAM_PATH)
    return {
        "route_z": float(p.GetFloat("route_z", DEFAULT_ROUTE_Z)),
        "bend_radius": float(p.GetFloat("bend_radius", DEFAULT_BEND_RADIUS)),
        "port_stub": float(p.GetFloat("port_stub", DEFAULT_PORT_STUB)),
        "diameter": float(p.GetFloat("diameter", DEFAULT_DIAMETER)),
    }


def _save_cfg(cfg):
    p = App.ParamGet(PARAM_PATH)
    for key, value in cfg.items():
        p.SetFloat(key, float(value))


def _run_dialog(circuit_map):
    cfg = _default_cfg()
    if (not GUI_UP) or QtWidgets is None:
        return cfg
    total_boxes = sum(len(data[1]) for data in circuit_map.values())
    expected = sum(max(0, len(data[1]) - 1) for data in circuit_map.values())
    dlg = QtWidgets.QDialog(Gui.getMainWindow()); dlg.setWindowTitle("Octogonales ortogonales TCOM"); dlg.setMinimumWidth(510)
    info = QtWidgets.QLabel("Circuitos: {} | cajas: {} | ramales: {}".format(len(circuit_map), total_boxes, expected))
    form = QtWidgets.QFormLayout(); controls = {}
    specs = [("route_z", "Altura:", 3001.0, 10000.0), ("bend_radius", "Radio:", 0.0, 1000.0), ("port_stub", "Salida desde caja:", 10.0, 500.0), ("diameter", "Diametro EMT:", 1.0, 200.0)]
    for key, label, minimum, maximum in specs:
        spin = QtWidgets.QDoubleSpinBox(); spin.setRange(minimum, maximum); spin.setDecimals(1); spin.setSuffix(" mm"); spin.setValue(cfg[key]); controls[key] = spin; form.addRow(label, spin)
    buttons = QtWidgets.QDialogButtonBox(QtWidgets.QDialogButtonBox.Ok | QtWidgets.QDialogButtonBox.Cancel); buttons.accepted.connect(dlg.accept); buttons.rejected.connect(dlg.reject)
    layout = QtWidgets.QVBoxLayout(dlg); layout.addWidget(info); layout.addLayout(form); layout.addWidget(buttons)
    execute = getattr(dlg, "exec", None) or getattr(dlg, "exec_", None)
    if execute() != QtWidgets.QDialog.Accepted:
        return None
    for key, control in controls.items(): cfg[key] = float(control.value())
    _save_cfg(cfg); return cfg


def main(doc_override=None, cfg_override=None):
    doc = doc_override or App.ActiveDocument
    if doc is None:
        _err("No hay documento activo."); return None
    circuit_map = _TCOM["_find_circuit_groups"](doc)
    if not circuit_map:
        _warn("No se encontraron circuitos TCOM."); return None
    cfg = dict(cfg_override) if cfg_override is not None else _run_dialog(circuit_map)
    if cfg is None:
        return None
    defaults = _default_cfg()
    for key in defaults: cfg[key] = float(cfg.get(key, defaults[key]))
    cfg["route_z"] = max(3001.0, cfg["route_z"])
    all_boxes = list({box.Name: box for _group, boxes in circuit_map.values() for box in boxes}.values())
    reserved = _reserved_ports(doc, all_boxes)
    used = {name: set(values) for name, values in reserved.items()}
    plans = []
    for number in sorted(circuit_map):
        group, boxes = circuit_map[number]
        circuit_id = "TCOM-%02d" % number
        edges = _TP["_minimum_spanning_edges"](boxes, _feeder_root(doc, circuit_id, boxes))
        plans.append((group, circuit_id, boxes, edges))

    valid_keys = set(); branches = []; created = updated = 0
    doc.openTransaction("ElectricCR: conectar octogonales ortogonal por circuito TCOM")
    try:
        for group, circuit_id, boxes, edges in plans:
            for index, (source, destination) in enumerate(edges, start=1):
                source_data = _TP["_choose_port"](source, _TP["_box_center_xy"](destination), used[source.Name]); used[source.Name].add(source_data[2])
                destination_data = _TP["_choose_port"](destination, _TP["_box_center_xy"](source), used[destination.Name]); used[destination.Name].add(destination_data[2])
                points = _TP["_branch_route"](source, destination, source_data[0], source_data[1], destination_data[0], destination_data[1], boxes, cfg)
                obj, was_created = _write_branch(doc, group, circuit_id, index, source, destination, source_data, destination_data, points, cfg)
                branches.append(obj); valid_keys.add(obj.ConexionKey); created += int(was_created); updated += int(not was_created)
            _log("{} | cajas={} | ramales={}".format(circuit_id, len(boxes), len(edges)))
        deleted = _delete_stale(doc, valid_keys); _cleanup_empty_groups(doc); doc.recompute(); doc.commitTransaction()
    except Exception as exc:
        try: doc.abortTransaction()
        except Exception: pass
        _err("Fallo general: " + str(exc)); return None
    result = {"circuitos": len(plans), "cajas": len(all_boxes), "ramales": len(branches), "creados": created, "actualizados": updated, "eliminados_obsoletos": deleted, "circuitos_una_caja": [cid for _g,cid,boxes,_edges in plans if len(boxes)==1]}
    _log("Finalizado: " + json.dumps(result, ensure_ascii=False)); return result


if __name__ == "__main__":
    main()

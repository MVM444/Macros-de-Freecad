# -*- coding: utf-8 -*-
"""
Name: Demo_ElectricCR_A1_Prueba_Arquitectura.FCMacro
Purpose: Ejecutar el tramo de la Demo ElectricCR A1 validado manualmente en FreeCAD 1.1.3.
Main behavior: crea un documento NUEVO con metadata, edificio, Nivel 00, losa y cinco muros BIM; se detiene antes de Spaces y dispositivos A1.
Future modifications: ampliar esta misma prueba solo despues de validar manualmente el siguiente tramo; no duplicar la logica del adaptador.
Version: 0.1.0
Date/time: 2026-09-09 23:14 America/Costa_Rica
Target: FreeCAD 1.1.3
"""

import FreeCAD as App

from ElectricCR.electriccr.demo.electric_demo_freecad import create_validated_scaffold

result = create_validated_scaffold()
doc = result["document"]

try:
    import FreeCADGui as Gui
    Gui.activeDocument().activeView().viewAxonometric()
    Gui.activeDocument().activeView().fitAll()
except Exception:
    pass

App.Console.PrintMessage(
    "[ElectricCR][Demo] PRUEBA ARQUITECTURA LISTA: metadata + edificio + Nivel 00 + losa + 5 muros. "
    "Siguiente frontera: Arch Spaces.\n"
)

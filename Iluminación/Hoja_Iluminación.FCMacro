# -*- coding: utf-8 -*-
# MenuText: Hoja Iluminacion
# ToolTip: Exporta luminarias por circuito a Spreadsheet

import importlib
import sys
from pathlib import Path


def _macro_dir():
    try:
        return Path(__file__).resolve().parent
    except Exception:
        return Path.cwd()


macro_dir = _macro_dir()
if str(macro_dir) not in sys.path:
    sys.path.insert(0, str(macro_dir))

import lighting_schedule_export as _lighting_schedule_export

_lighting_schedule_export = importlib.reload(_lighting_schedule_export)
_lighting_schedule_export.export_lighting_schedule()

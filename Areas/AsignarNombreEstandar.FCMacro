# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

# Macro: AsignarNombreEstandar.FCMacro
# Descripcion:
# Esta macro muestra una ventana flotante con botones por cada nombre estandar definido en una hoja de calculo.
# Al hacer clic en un boton, todos los objetos seleccionados en FreeCAD seran renombrados con ese nombre.
# Si el nombre ya fue usado (marcado con fondo gris), se muestra una advertencia, pero se permite su reutilizacion.
# La hoja editable "NombresEstandar" permite personalizar los nombres.
#
# Fecha: 2025-07-05
# Requiere: FreeCADGui y PySide/PySide2

import FreeCAD
import FreeCADGui
import math

try:
    from PySide2 import QtWidgets, QtCore
except Exception:
    try:
        from PySide import QtCore, QtGui
        QtWidgets = QtGui
    except Exception:
        from PySide6 import QtWidgets, QtCore

# Obtener documento
doc = FreeCAD.ActiveDocument
if doc is None:
    doc = FreeCAD.newDocument("Proyecto")

nombre_hoja = "NombresEstandar"
grupo_hojas_nombre = "Hojas_de_Calculo"
grupo_hojas_label = "Hojas de Calculo"
grupo_hojas_aliases = ("Hojas de Calculo", "Hojas de Cálculo", "Hojas_Calculo")


def texto_objeto(obj):
    try:
        return str(obj or "").strip()
    except Exception:
        return ""


def objeto_es_grupo(obj):
    return hasattr(obj, "Group")


def nombre_visible(obj):
    label = texto_objeto(getattr(obj, "Label", ""))
    if label:
        return label
    return texto_objeto(getattr(obj, "Name", ""))


def buscar_grupo_hojas():
    aliases = set(alias.lower() for alias in grupo_hojas_aliases)
    for obj in doc.Objects:
        if objeto_es_grupo(obj) and nombre_visible(obj).lower() in aliases:
            return obj
    return None


def asegurar_grupo_hojas():
    grupo = buscar_grupo_hojas()
    if grupo is not None:
        return grupo
    grupo = doc.addObject("App::DocumentObjectGroup", grupo_hojas_nombre)
    grupo.Label = grupo_hojas_label
    FreeCAD.Console.PrintMessage("Se creo el grupo 'Hojas de Calculo'.\n")
    return grupo


def asegurar_hoja_en_grupo(hoja):
    grupo = asegurar_grupo_hojas()
    try:
        if hoja not in list(getattr(grupo, "Group", [])):
            grupo.addObject(hoja)
            FreeCAD.Console.PrintMessage("La hoja 'NombresEstandar' se ubico en el grupo 'Hojas de Calculo'.\n")
    except Exception:
        try:
            grupo.addObject(hoja)
        except Exception:
            FreeCAD.Console.PrintMessage("No se pudo mover 'NombresEstandar' al grupo 'Hojas de Calculo'.\n")
    return hoja


def obtener_hoja():
    crear_hoja = not hasattr(doc, nombre_hoja)
    if crear_hoja:
        hoja = doc.addObject("Spreadsheet::Sheet", nombre_hoja)
        hoja.set("A1", "Oficina")
        hoja.set("A2", "Sala de Espera")
        hoja.set("A3", "Bodega")
        hoja.set("A4", "Recepcion")
        hoja.set("A5", "Pasillo")
        doc.recompute()
        FreeCAD.Console.PrintMessage("Se creo la hoja 'NombresEstandar' con nombres iniciales.\n")
        return asegurar_hoja_en_grupo(hoja)
    return asegurar_hoja_en_grupo(getattr(doc, nombre_hoja))


def celda_marcada(hoja, celda):
    try:
        estilo = hoja.getStyle(celda)
    except Exception:
        return False
    if estilo is None:
        return False
    if isinstance(estilo, str):
        return "#dddddd" in estilo.lower()
    if isinstance(estilo, set):
        return any("#dddddd" in s.lower() for s in estilo if isinstance(s, str))
    return False


def leer_nombres():
    hoja = obtener_hoja()
    nombres = []
    marcados = []
    fila = 1
    while True:
        celda = "A{}".format(fila)
        try:
            valor = hoja.get(celda)
        except Exception:
            break
        if valor == "":
            break
        nombres.append(valor)
        marcados.append(celda_marcada(hoja, celda))
        fila += 1
    return hoja, nombres, marcados

# Crear ventana con botones en varias columnas
class VentanaNombres(QtWidgets.QDialog):
    def __init__(self):
        super().__init__(None, QtCore.Qt.Tool)
        self.setWindowTitle("Asignar Nombre Estandar")
        self.setSizeGripEnabled(True)
        self.setWindowFlags(self.windowFlags() | QtCore.Qt.WindowStaysOnTopHint)
        self.hoja = None
        self.nombres = []
        self.marcados = []

        layout_principal = QtWidgets.QVBoxLayout(self)
        self.scroll = QtWidgets.QScrollArea()
        self.scroll.setWidgetResizable(False)
        self.contenedor = QtWidgets.QWidget()
        self.grid = QtWidgets.QGridLayout(self.contenedor)
        self.grid.setContentsMargins(4, 4, 4, 4)

        self.botones = []
        self.scroll.setWidget(self.contenedor)
        layout_principal.addWidget(self.scroll)

        fila_acciones = QtWidgets.QHBoxLayout()
        self.boton_actualizar = QtWidgets.QPushButton("Actualizar")
        self.boton_cerrar = QtWidgets.QPushButton("Cerrar")
        self.boton_actualizar.clicked.connect(self.actualizar_desde_hoja)
        self.boton_cerrar.clicked.connect(self.close)
        fila_acciones.addWidget(self.boton_actualizar)
        fila_acciones.addWidget(self.boton_cerrar)
        layout_principal.addLayout(fila_acciones)

        self.actualizar_desde_hoja(inicial=True)

    def mostrar_mensaje(self, icono, titulo, texto):
        cuadro = QtWidgets.QMessageBox(self)
        cuadro.setIcon(icono)
        cuadro.setWindowTitle(titulo)
        cuadro.setText(texto)
        cuadro.setStandardButtons(QtWidgets.QMessageBox.Ok)
        try:
            cuadro.setWindowModality(QtCore.Qt.WindowModal)
        except Exception:
            pass
        try:
            cuadro.setWindowFlags(cuadro.windowFlags() | QtCore.Qt.WindowStaysOnTopHint)
        except Exception:
            pass
        if hasattr(cuadro, "exec_"):
            cuadro.exec_()
        else:
            cuadro.exec()

    def limpiar_botones(self):
        while self.grid.count():
            item = self.grid.takeAt(0)
            widget = item.widget()
            if widget:
                widget.deleteLater()
        self.botones = []

    def columnas_para_botones(self):
        total = len(self.nombres)
        if total <= 4:
            return 1
        return max(2, min(4, int(math.ceil(math.sqrt(total)))))

    def reconstruir_botones(self):
        self.limpiar_botones()
        columnas = self.columnas_para_botones()
        for i, nombre in enumerate(self.nombres):
            boton = QtWidgets.QPushButton(nombre)
            boton.setMinimumWidth(120)
            if self.marcados[i]:
                boton.setStyleSheet("background-color: #dddddd")
            boton.clicked.connect(lambda checked=False, n=nombre, f=i, b=boton: self.renombrar(n, f, b))
            fila = i // columnas
            col = i % columnas
            self.grid.addWidget(boton, fila, col)
            self.botones.append(boton)
        self.contenedor.adjustSize()
        self.ajustar_tamano()

    def ajustar_tamano(self):
        hint = self.contenedor.sizeHint()
        ancho = max(260, min(hint.width() + 40, 760))
        alto_scroll = max(80, min(hint.height() + 20, 520))
        self.scroll.setMinimumWidth(ancho)
        self.scroll.setMinimumHeight(alto_scroll)
        self.scroll.resize(ancho, alto_scroll)
        self.adjustSize()

    def actualizar_desde_hoja(self, inicial=False):
        self.hoja, self.nombres, self.marcados = leer_nombres()
        self.reconstruir_botones()
        if not self.nombres:
            self.mostrar_mensaje(QtWidgets.QMessageBox.Warning, "Error", "La hoja 'NombresEstandar' no contiene nombres.")
        elif not inicial:
            FreeCAD.Console.PrintMessage("Lista de nombres actualizada desde 'NombresEstandar'.\n")

    def renombrar(self, nombre, fila_index, boton):
        seleccion = FreeCADGui.Selection.getSelection()
        if not seleccion:
            self.mostrar_mensaje(QtWidgets.QMessageBox.Warning, "Sin seleccion", "No hay objetos seleccionados.")
            return

        if self.marcados[fila_index]:
            self.mostrar_mensaje(QtWidgets.QMessageBox.Information, "Advertencia", f"El nombre '{nombre}' ya ha sido utilizado.")

        for obj in seleccion:
            anterior = obj.Label
            obj.Label = nombre
            FreeCAD.Console.PrintMessage(f"Objeto '{anterior}' renombrado como '{nombre}'.\n")

        try:
            self.hoja.setStyle(f"A{fila_index+1}", "background-color: #DDDDDD")
            boton.setStyleSheet("background-color: #dddddd")
            self.marcados[fila_index] = True
        except Exception:
            FreeCAD.Console.PrintMessage(f"No se pudo marcar visualmente el nombre '{nombre}'.\n")

        doc.recompute()

ventana = VentanaNombres()
ventana.setWindowModality(QtCore.Qt.NonModal)
ventana.show()

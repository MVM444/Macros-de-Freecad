# -*- coding: utf-8 -*-
# MenuText: Recalcular Distribucion de Luminarias
# ToolTip: Marca las areas seleccionadas para recalcular filas y columnas en la proxima actualizacion
# Icon: Recalcular_Distribucion_Luminarias_Areas.svg

import FreeCAD as App
import FreeCADGui as Gui

try:
    from PySide6 import QtWidgets
except Exception:
    try:
        from PySide2 import QtWidgets
    except Exception:
        from PySide import QtGui as QtWidgets


def _is_rectangle(obj):
    return getattr(getattr(obj, "Proxy", None), "Type", "") == "Rectangle"


def _collect(items):
    result, seen = [], set()
    def visit(obj):
        name = getattr(obj, "Name", "")
        if not name or name in seen:
            return
        seen.add(name)
        if _is_rectangle(obj):
            result.append(obj)
        for child in getattr(obj, "Group", []) or []:
            visit(child)
    for item in items:
        visit(item)
    return result


def run():
    doc = App.ActiveDocument
    if doc is None:
        QtWidgets.QMessageBox.warning(None, "ElectricCR", "No hay un documento activo.")
        return
    areas = _collect(Gui.Selection.getSelection() or [])
    if not areas:
        QtWidgets.QMessageBox.warning(None, "ElectricCR", "Seleccione las areas que desea recalcular.")
        return
    doc.openTransaction("ElectricCR: Solicitar recalculo de luminarias")
    try:
        for area in areas:
            if "LightingRecalculateLayout" not in area.PropertiesList:
                area.addProperty("App::PropertyBool", "LightingRecalculateLayout", "ElectricCR Iluminacion")
            area.LightingRecalculateLayout = True
        doc.recompute()
        doc.commitTransaction()
    except Exception:
        doc.abortTransaction()
        raise
    QtWidgets.QMessageBox.information(
        Gui.getMainWindow(), "ElectricCR",
        "{} area(s) se recalcularan al ejecutar Actualizar Iluminacion Completa.".format(len(areas)),
    )


run()

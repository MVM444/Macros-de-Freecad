#!/usr/bin/env python
# -*- coding: utf-8 -*-
# Icon: InsertarTomacorriente.svg
"""
Insertar_Tomacorriente.FCMacro (factory-only)

Macro de inserción que delega completamente en Electric_Principal.FCMacro.

Qué hace:
- Carga el módulo principal (Electric_Principal.FCMacro).
- Llama a create_objeto_electromecanico() con parámetros por defecto para un tomacorriente.
- No redefine clases, enumeraciones ni lógica de transformaciones.
- Registra logs en la consola con prefijo [ELEC].

Uso:
- Ejecutar sobre una cara vertical (pared) para orientar el tomacorriente.
- Cambiar propiedades en el panel de datos (ModoVisual, AlturaRel, MontajePared, etc.).

Historial de cambios:
- v1 (2025-09-17): Versión inicial simplificada, sin clases duplicadas.
- v2 (2025-09-17): Comentarios mejorados; se aclara flujo de carga y defaults aplicados.
"""

import FreeCAD as App
import os
import types

LOG_TAG = "[ELEC]"


def _info(msg):
    App.Console.PrintMessage(f"{LOG_TAG}[INFO] {msg}\n")


def _err(msg):
    App.Console.PrintError(f"{LOG_TAG}[ERROR] {msg}\n")


# --- carga de Electric_Principal.FCMacro ---

def _candidate_principal_paths():
    """Genera rutas candidatas para buscar Electric_Principal.FCMacro."""
    paths = []
    try:
        here = os.path.dirname(os.path.abspath(__file__))
        paths.append(os.path.join(here, "..", "Electric_Principal.FCMacro"))
        paths.append(os.path.join(here, "Electric_Principal.FCMacro"))
    except Exception:
        pass
    macro_dirs = []
    try:
        user_dir = App.getUserMacroDir()
        if user_dir:
            macro_dirs.append(user_dir)
    except Exception:
        pass
    try:
        sep = ";" if os.name == "nt" else ":"
        mp = App.ParamGet("User parameter:BaseApp/Preferences/Macro").GetString("MacroPath", "")
        for entry in mp.split(sep):
            entry = entry.strip()
            if entry:
                macro_dirs.append(entry)
    except Exception:
        pass
    for base in macro_dirs:
        paths.extend([
            os.path.join(base, "Electric_Principal.FCMacro"),
            os.path.join(base, "Electric", "Electric_Principal.FCMacro"),
            os.path.join(base, "Macros-de-Freecad", "Electric", "Electric_Principal.FCMacro"),
        ])
    uniq = []
    seen = set()
    for p in paths:
        ap = os.path.abspath(p)
        if ap not in seen:
            seen.add(ap)
            uniq.append(ap)
    return uniq


def _load_module_from_path(path):
    """Carga el archivo principal como un módulo temporal."""
    try:
        with open(path, "r", encoding="utf-8") as fh:
            source = fh.read()
    except Exception as exc:
        _err(f"no se pudo leer {path}: {exc}")
        return None
    module = types.ModuleType("Electric_Principal")
    module.__file__ = path
    try:
        exec(compile(source, path, "exec"), module.__dict__)
        return module
    except Exception as exc:
        _err(f"fallo al ejecutar principal en {path}: {exc}")
        return None


def _load_principal():
    """Itera sobre las rutas candidatas y devuelve el módulo cargado."""
    for path in _candidate_principal_paths():
        if os.path.exists(path):
            mod = _load_module_from_path(path)
            if mod is not None:
                _info(f"cargado principal: {path}")
                return mod
    _err("Electric_Principal.FCMacro no encontrado")
    return None


# --- API pública ---

def insertar_tomacorriente(params=None):
    """Crea un tomacorriente usando la fábrica genérica del principal."""
    mod = _load_principal()
    if mod is None:
        return None

    # Defaults de inserción
    defaults = {
        "Categoria": "Pared",
        "Tipo": "Toma",
        "ModoVisual": "Ambos",          # válido en principal
        "AlturaRel": 300,                 # mm sobre nivel
        "MontajePared": "Sobrepuesto",   # o "Empotrado"
        "EtiquetaPlano": "Toma",
        "CircuitoID": "CIR-01",
    }
    if params:
        defaults.update(params)

    obj = mod.create_objeto_electromecanico(defaults)
    if obj is not None:
        _info(f"insertado {obj.Label}")
    return obj


if __name__ == "__main__":
    insertar_tomacorriente()

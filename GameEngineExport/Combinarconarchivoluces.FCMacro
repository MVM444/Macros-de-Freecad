# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

# Macro: CombinarLucesEdificio.FCMacro
# Descripcion:
# Permite seleccionar mediante un dialogo de archivos el modelo de edificio y el modelo de luces, y guarda el archivo X3D combinado.
# Autor: GPT + Usuario
# Fecha: 2025-07-12

import os
import FreeCAD
import FreeCADGui
from PySide import QtWidgets


def combine_x3d():
    # Dialogo para seleccionar archivo de edificio
    edificio_path, filtro1 = QtWidgets.QFileDialog.getOpenFileName(
        None,
        "Seleccionar archivo de edificio",
        "",
        "X3D Files (*.x3d);;Collada Files (*.dae)"
    )
    if not edificio_path:
        FreeCAD.Console.PrintMessage("Operacion cancelada: no se selecciono archivo de edificio.\n")
        return

    # Dialogo para seleccionar archivo de luces
    luces_path, filtro2 = QtWidgets.QFileDialog.getOpenFileName(
        None,
        "Seleccionar archivo de luces",
        "",
        "X3D Files (*.x3d)"
    )
    if not luces_path:
        FreeCAD.Console.PrintMessage("Operacion cancelada: no se selecciono archivo de luces.\n")
        return

    # Dialogo para guardar archivo combinado
    salida_path, filtro3 = QtWidgets.QFileDialog.getSaveFileName(
        None,
        "Guardar archivo combinado",
        "Puriscal_con_luces.x3d",
        "X3D Files (*.x3d)"
    )
    if not salida_path:
        FreeCAD.Console.PrintMessage("Operacion cancelada: no se selecciono destino de guardado.\n")
        return

    # Leer contenido de edificio y luces
    with open(edificio_path, 'r', encoding='utf-8') as f:
        contenido_edificio = f.read()
    with open(luces_path, 'r', encoding='utf-8') as f:
        contenido_luces = f.read()

    # Extraer nodos de luces dentro de <Scene>...
    inicio = contenido_luces.find('<Scene>') + len('<Scene>')
    fin = contenido_luces.find('</Scene>')
    luces_snippet = contenido_luces[inicio:fin].strip()

    # Insertar antes de </Scene> del edificio
    idx_final = contenido_edificio.rfind('</Scene>')
    combinado = (
        contenido_edificio[:idx_final].rstrip() +
        "\n  <!-- Luces insertadas -->\n  " + luces_snippet +
        "\n" + contenido_edificio[idx_final:]
    )

    # Guardar archivo combinado
    with open(salida_path, 'w', encoding='utf-8') as f:
        f.write(combinado)

    FreeCAD.Console.PrintMessage(f"Archivo combinado guardado en: {salida_path}\n")

# Ejecutar la función
combine_x3d()

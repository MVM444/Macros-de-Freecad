# Icon: medir_distancia_y_dibujar_ruta_independiente.svg

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()


# ------------------------------------------------------------------------
# RESUMEN:
# Esta macro calcula distancias y dibuja rutas ortogonales entre un objeto
# inicial y cada equipo de un grupo en FreeCAD usando Draft Wire.
# ------------------------------------------------------------------------

import FreeCAD
import FreeCADGui
import Draft
import os
import sys
_THIS_DIR = os.path.dirname(__file__) if '__file__' in globals() else ''
if _THIS_DIR and _THIS_DIR not in sys.path:
    sys.path.insert(0, _THIS_DIR)
import importlib
import conexiones_grouping as _conexiones_grouping_mod
_conexiones_grouping_mod = importlib.reload(_conexiones_grouping_mod)
ensure_conexiones_group = _conexiones_grouping_mod.ensure_conexiones_group
import component_classifier as _component_classifier_mod
_component_classifier_mod = importlib.reload(_component_classifier_mod)
try:
    from PySide2 import QtWidgets as QtGui
except Exception:
    from PySide import QtGui

def _to_float(value, default=0.0):
    try:
        return float(value)
    except Exception:
        pass
    try:
        return float(getattr(value, "Value", default))
    except Exception:
        return default

def _altura_rel_obj(obj):
    for prop_name in ("AlturaRel", "Altura", "Elevation", "Elevacion", "Z"):
        if hasattr(obj, prop_name):
            try:
                return _to_float(getattr(obj, prop_name), 0.0)
            except Exception:
                pass
    return 0.0

def _conn_point(obj):
    if not hasattr(obj, "Placement"):
        return FreeCAD.Vector(0, 0, 0)
    p = obj.Placement.Base
    z = _to_float(p.z, 0.0) + _altura_rel_obj(obj)
    return FreeCAD.Vector(_to_float(p.x, 0.0), _to_float(p.y, 0.0), z)

def _route_z_level(z_height, p_start, p_end):
    z_req = _to_float(z_height, 0.0)
    return max(z_req, _to_float(p_start.z, 0.0), _to_float(p_end.z, 0.0))

def _is_non_socket_annotation(obj):
    lab = str(getattr(obj, "Label", "") or "").strip().lower()
    nam = str(getattr(obj, "Name", "") or "").strip().lower()
    txt = f"{lab} {nam}"
    if "etiqueta" in txt:
        return True
    if txt.startswith("conexion") or " conexion" in txt:
        return True
    return False


def _make_wire(points):
    maker = getattr(Draft, "make_wire", None)
    if maker is None:
        maker = getattr(Draft, "makeWire", None)
    if maker is None:
        raise RuntimeError("No se encontro Draft.make_wire ni Draft.makeWire")

    attempts = [
        lambda: maker(points, closed=False, face=False),
        lambda: maker(points, False, False),
        lambda: maker(points, False),
        lambda: maker(points),
    ]
    last_err = None
    for attempt in attempts:
        try:
            return attempt()
        except Exception as ex:
            last_err = ex
    raise RuntimeError(f"No se pudo crear wire: {last_err}")


def medir_distancia_y_dibujar_ruta_independiente():
    doc = FreeCAD.ActiveDocument
    if doc is None:
        FreeCAD.Console.PrintError("No hay documento activo.\n")
        return

    selection = FreeCADGui.Selection.getSelection()

    if len(selection) < 2:
        FreeCAD.Console.PrintError("Debe seleccionar un objeto inicial y un grupo de equipos.\n")
        return

    objeto_inicial = selection[0]
    if not hasattr(objeto_inicial, "Placement"):
        FreeCAD.Console.PrintError("El objeto inicial no tiene Placement.\n")
        return

    grupo_equipos = selection[1]
    if not hasattr(grupo_equipos, "Group"):
        FreeCAD.Console.PrintError("Debe seleccionar un grupo como segundo objeto.\n")
        return

    if not hasattr(doc, "ResultadosEquiposIndependientes"):
        hoja = doc.addObject("Spreadsheet::Sheet", "ResultadosEquiposIndependientes")
        hoja.set("A1", "Equipo")
        hoja.set("B1", "Distancia (mm)")
    else:
        hoja = doc.ResultadosEquiposIndependientes

    dialog = QtGui.QInputDialog()
    altura, ok = dialog.getDouble(None, "Altura", "Ingrese la altura (mm):", 3000, -10000, 10000, 2)
    if not ok:
        return

    fila = 2

    equipos = []
    for obj in grupo_equipos.Group:
        if not hasattr(obj, "Placement"):
            continue
        if _is_non_socket_annotation(obj):
            continue
        try:
            if _component_classifier_mod.is_toma(obj):
                equipos.append(obj)
                continue
        except Exception:
            pass
        lbl = str(getattr(obj, "Label", "") or "").lower()
        nam = str(getattr(obj, "Name", "") or "").lower()
        if ("tomacorriente" in lbl) or ("tomacorriente" in nam) or lbl.startswith("toma") or nam.startswith("toma"):
            equipos.append(obj)
    if not equipos:
        FreeCAD.Console.PrintError("No se encontraron equipos en el grupo seleccionado.\n")
        return

    grupo_conexiones = ensure_conexiones_group(doc, parent_group=grupo_equipos, objects=equipos)

    p_ini = _conn_point(objeto_inicial)
    for equipo in equipos:
        p_fin = _conn_point(equipo)
        distancia = p_ini.distanceToPoint(p_fin)

        hoja.set(f"A{fila}", equipo.Label)
        hoja.set(f"B{fila}", str(round(distancia, 2)))
        fila += 1

        FreeCAD.Console.PrintMessage(f"Equipo: {equipo.Label}, Distancia: {distancia} mm\n")

        z_ruta = _route_z_level(altura, p_ini, p_fin)
        puntos = [
            p_ini,
            FreeCAD.Vector(p_ini.x, p_ini.y, z_ruta),
            FreeCAD.Vector(p_fin.x, p_ini.y, z_ruta),
            FreeCAD.Vector(p_fin.x, p_fin.y, z_ruta),
            p_fin,
        ]

        wire = _make_wire(puntos)
        wire.Label = f"Ruta Critica hacia {equipo.Label}"

        if hasattr(wire, "FilletRadius"):
            try:
                wire.FilletRadius = 500.0
            except Exception as ex:
                FreeCAD.Console.PrintWarning(f"No se pudo aplicar FilletRadius: {ex}\n")

        grupo_conexiones.addObject(wire)

    doc.recompute()


# Ejecutar la macro
medir_distancia_y_dibujar_ruta_independiente()

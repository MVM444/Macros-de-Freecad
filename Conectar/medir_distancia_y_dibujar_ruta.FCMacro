# -*- coding: utf-8 -*-
# Icon: medir_distancia_y_dibujar_ruta.svg

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

# ------------------------------------------------------------------------
# NOMBRE MACRO: RutaCritica_WIRE.FCMacro
# UBICACION: directorio de macros de FreeCAD
#
# DESCRIPCION:
#   Traza un Draft WIRE ortogonal desde un objeto inicial hacia la toma
#   mas lejana en cada subgrupo del grupo seleccionado. Registra datos
#   en la hoja "ResultadosRutaCritica" SIN borrar filas existentes.
#
# INSTRUCCIONES:
#   1) Seleccione primero el objeto inicial (con Placement).
#   2) Seleccione despues el grupo que contiene las tomas (puede tener subgrupos).
#   3) Ingrese la altura Z (mm) para rutear.
#
# NOTAS:
#   - Sin tildes ni caracteres especiales en codigo y comentarios.
#   - Depuracion en consola con prefijo [RUTA].
#   - Se omiten grupos "Conexiones*" y objetos "Ruta Critica*".
#   - E1 mantiene la proxima fila; esta corrida escribe en bloque y al final actualiza E1.
# ------------------------------------------------------------------------

import FreeCAD
import FreeCADGui
import Draft
from PySide import QtGui
from datetime import datetime
import os
import sys
_THIS_DIR = os.path.dirname(__file__) if '__file__' in globals() else ''
if _THIS_DIR and _THIS_DIR not in sys.path:
    sys.path.insert(0, _THIS_DIR)
import importlib
import conexiones_grouping as _conexiones_grouping_mod
_conexiones_grouping_mod = importlib.reload(_conexiones_grouping_mod)
_ensure_conexiones_group_unified = _conexiones_grouping_mod.ensure_conexiones_group
import component_classifier as _component_classifier_mod
_component_classifier_mod = importlib.reload(_component_classifier_mod)
TAG = "[RUTA]"
WRITE_RESULTS_SHEET = False

def log_info(msg): FreeCAD.Console.PrintMessage(f"{TAG}[INFO] {msg}\n")
def log_warn(msg): FreeCAD.Console.PrintWarning(f"{TAG}[WARN] {msg}\n")
def log_err(msg):  FreeCAD.Console.PrintError(f"{TAG}[ERROR] {msg}\n")

# ---------------------- Spreadsheet helpers -----------------------------

def set_text(sheet, addr, text):
    # texto entre comillas para evitar interpretacion como expresion
    s = '"' + str(text).replace('"', '""') + '"'
    sheet.set(addr, s)

def set_number(sheet, addr, num, decimals=2):
    # escribir numero como string simple (con decimales si aplica)
    if isinstance(num, float):
        s = f"{num:.{decimals}f}"
    else:
        s = str(num)
    sheet.set(addr, s)

def ensure_results_sheet(doc):
    sheet = getattr(doc, "ResultadosRutaCritica", None)
    if sheet is None:
        sheet = doc.addObject("Spreadsheet::Sheet", "ResultadosRutaCritica")
        set_text(sheet, "A1", "Circuito")
        set_text(sheet, "B1", "Toma_mas_lejana")
        set_text(sheet, "C1", "Distancia_mm")
        set_text(sheet, "D1", "WireName")
        sheet.set("E1", "2")  # proxima fila como texto simple
        log_info("Hoja 'ResultadosRutaCritica' creada")
    else:
        try:
            v = sheet.get("E1")
            if v is None or str(v).strip() == "":
                sheet.set("E1", "2")
        except Exception:
            sheet.set("E1", "2")
        log_info("Hoja 'ResultadosRutaCritica' encontrada")
    return sheet

def _parse_e1_to_row(v):
    # saneo de E1: sin comillas, >=2
    if v is None:
        return 2
    s = str(v).strip()
    if s.startswith('"') and s.endswith('"') and len(s) >= 2:
        s = s[1:-1]
    s = s.strip()
    try:
        r = int(float(s))
    except Exception:
        r = 2
    if r < 2:
        r = 2
    return r

def _cell_is_empty(sheet, row):
    # fila vacia si A..D estan vacias; si hay error de lectura, asumimos vacia
    for col in ("A","B","C","D"):
        try:
            val = sheet.get(f"{col}{row}")
        except Exception:
            return True
        if val not in (None, "") and str(val).strip() != "":
            return False
    return True

def find_block_start_row(sheet, start_row, max_scan=10000):
    """
    Busca UNA SOLA VEZ la primera fila realmente vacia a partir de start_row.
    Limita el escaneo para evitar tiempos largos.
    """
    row = max(2, int(start_row))
    if row > 100000:
        log_warn(f"E1 demasiado grande ({row}); reseteo a 2")
        row = 2
    limit = row + max_scan
    while row <= limit:
        if _cell_is_empty(sheet, row):
            return row
        row += 1
    log_warn("Scan limitado alcanzado; se usara ultima fila evaluada")
    return limit

def bump_e1(sheet, new_next_row):
    try:
        sheet.set("E1", str(int(new_next_row)))
    except Exception as ex:
        log_warn(f"No se pudo actualizar E1 a {new_next_row}: {ex}")

# ------------------------ Group helpers ---------------------------------

def is_conexiones_group(g):
    label = getattr(g, "Label", "")
    name  = getattr(g, "Name", "")
    return (isinstance(label, str) and label.startswith("Conexiones")) or \
           (isinstance(name, str)  and name.startswith("Conexiones"))

def ensure_conexiones_group(doc, parent_group):
    g = _ensure_conexiones_group_unified(doc, parent_group=parent_group)
    try:
        log_info(f"Destino de conexiones: {getattr(g, 'Label', getattr(g, 'Name', 'Conexiones'))}")
    except Exception:
        pass
    return g

def collect_groups_to_evaluate(grupo):
    if hasattr(grupo, "Group") and len(grupo.Group) > 0:
        subs = [g for g in grupo.Group if hasattr(g, "Group") and not is_conexiones_group(g)]
        if len(subs) > 0:
            return subs
    return [] if is_conexiones_group(grupo) else [grupo]

# ------------------------- Geometry helpers -----------------------------

def _to_float(value, default=0.0):
    try:
        return float(value)
    except Exception:
        pass
    try:
        return float(getattr(value, "Value", default))
    except Exception:
        return default

def _altura_rel_obj(obj):
    for prop_name in ("AlturaRel", "Altura", "Elevation", "Elevacion", "Z"):
        if hasattr(obj, prop_name):
            try:
                return _to_float(getattr(obj, prop_name), 0.0)
            except Exception:
                pass
    return 0.0

def get_connection_point(obj):
    """
    Punto de conexion base:
    - X/Y: Placement.Base
    - Z: Placement.Base.z + altura relativa del objeto (si existe)
    """
    if not hasattr(obj, "Placement"):
        return FreeCAD.Vector(0, 0, 0)
    p = obj.Placement.Base
    z = _to_float(p.z, 0.0) + _altura_rel_obj(obj)
    return FreeCAD.Vector(_to_float(p.x, 0.0), _to_float(p.y, 0.0), z)

def route_z_level(z_height, p_start, p_end):
    # nunca rutear por debajo de inicio/fin
    z_req = _to_float(z_height, 0.0)
    return max(z_req, _to_float(p_start.z, 0.0), _to_float(p_end.z, 0.0))

def ortho_points_path(p_start, p_end, z_height):
    z_route = route_z_level(z_height, p_start, p_end)
    pts = []
    pts.append(p_start)
    pts.append(FreeCAD.Vector(p_start.x, p_start.y, z_route))
    pts.append(FreeCAD.Vector(p_end.x,   p_start.y, z_route))
    pts.append(FreeCAD.Vector(p_end.x,   p_end.y,   z_route))
    pts.append(p_end)
    return pts

def is_ruta_obj(obj):
    lab = getattr(obj, "Label", "")
    nam = getattr(obj, "Name", "")
    return (isinstance(lab, str) and lab.startswith("Ruta Critica")) or \
           (isinstance(nam, str) and nam.startswith("Ruta_Critica"))

def is_non_socket_annotation(obj):
    lab = str(getattr(obj, "Label", "") or "").strip().lower()
    nam = str(getattr(obj, "Name", "") or "").strip().lower()
    txt = f"{lab} {nam}"
    if "etiqueta" in txt:
        return True
    if txt.startswith("conexion") or " conexion" in txt:
        return True
    return False

def get_candidate_tomas(group_like):
    if not hasattr(group_like, "Group"):
        return []
    out_tomas = []
    for o in group_like.Group:
        if hasattr(o, "Placement") and not hasattr(o, "Group") and not is_ruta_obj(o):
            if is_non_socket_annotation(o):
                continue
            try:
                if _component_classifier_mod.is_toma(o):
                    out_tomas.append(o)
            except Exception:
                # Fallback legacy estricto por nombre/label
                lbl = str(getattr(o, "Label", "") or "").lower()
                nam = str(getattr(o, "Name", "") or "").lower()
                if ("tomacorriente" in lbl) or ("tomacorriente" in nam) or lbl.startswith("toma") or nam.startswith("toma"):
                    out_tomas.append(o)
    return out_tomas

# ---------------------- Draft wire compatibility ------------------------

def create_draft_wire(points_list):
    maker = getattr(Draft, "make_wire", None)
    if maker is None:
        maker = getattr(Draft, "makeWire", None)
    if maker is None:
        raise RuntimeError("No se encontro Draft.make_wire ni Draft.makeWire")

    attempts = [
        lambda: maker(points_list, False, False, None),
        lambda: maker(points_list, False, False),
        lambda: maker(points_list, False),
        lambda: maker(points_list)
    ]
    last_err = None
    for i, attempt in enumerate(attempts, 1):
        try:
            w = attempt()
            return w
        except Exception as ex:
            last_err = ex
            log_warn(f"Intento firma makeWire #{i} fallo: {ex}")
    raise TypeError(f"No fue posible crear el Wire con las firmas conocidas: {last_err}")

# ----------------------------- Main -------------------------------------

def _selected_objects():
    sel = list(FreeCADGui.Selection.getSelection() or [])
    if sel:
        return sel
    try:
        sel_ex = FreeCADGui.Selection.getSelectionEx() or []
        return [s.Object for s in sel_ex if getattr(s, "Object", None)]
    except Exception:
        return []

def run_ruta_critica(
    objeto_inicial,
    grupo_tomas,
    altura,
    hoja=None,
    base_row=None,
    recompute=True,
    update_e1=True,
    write_sheet=True,
):
    doc = FreeCAD.ActiveDocument
    if doc is None:
        raise RuntimeError("No hay documento activo")
    if not hasattr(objeto_inicial, "Placement"):
        raise RuntimeError("El objeto inicial no tiene Placement")
    if not hasattr(grupo_tomas, "Group"):
        raise RuntimeError("El grupo de tomas no es valido")

    if write_sheet and hoja is None:
        hoja = ensure_results_sheet(doc)
    grupos = collect_groups_to_evaluate(grupo_tomas)
    log_info(f"Grupos a evaluar: {len(grupos)}")

    if write_sheet and base_row is None:
        try:
            e1_val = hoja.get("E1")
        except Exception:
            e1_val = None
        start_row = _parse_e1_to_row(e1_val)
        base_row  = find_block_start_row(hoja, start_row, max_scan=10000)
    if write_sheet:
        log_info(f"Fila base para esta corrida: {base_row}")

    base0 = get_connection_point(objeto_inicial)
    wrote = 0

    for subg in grupos:
        g_label = getattr(subg, "Label", "Grupo")
        tomas = get_candidate_tomas(subg if hasattr(subg, "Group") else grupo_tomas)
        if len(tomas) == 0:
            log_warn(f"Sin objetos candidatos en '{g_label}', se omite")
            continue

        max_d = -1.0
        toma_far = None
        for t in tomas:
            try:
                p_toma = get_connection_point(t)
                d = base0.distanceToPoint(p_toma)
            except Exception as ex:
                log_warn(f"Omitiendo '{t.Label}' por error al medir: {ex}")
                continue
            if d > max_d:
                max_d = d
                toma_far = t

        if toma_far is None:
            log_warn(f"No se encontro toma valida en '{g_label}'")
            continue

        row = None
        if write_sheet:
            row = base_row + wrote
            log_info(f"Escribiendo fila {row} para '{g_label}'")
            try:
                set_text(hoja, f"A{row}", g_label)
                set_text(hoja, f"B{row}", toma_far.Label)
                set_number(hoja, f"C{row}", round(max_d, 2), decimals=2)
            except Exception as ex:
                log_err(f"Error escribiendo en fila {row}: {ex}")
                row = row + 1
                try:
                    set_text(hoja, f"A{row}", g_label)
                    set_text(hoja, f"B{row}", toma_far.Label)
                    set_number(hoja, f"C{row}", round(max_d, 2), decimals=2)
                    log_warn(f"Escritura recuperada en fila {row}")
                except Exception as ex2:
                    log_err(f"Fallo escritura de respaldo en fila {row}: {ex2}")
                    continue

        p_end = get_connection_point(toma_far)
        z_route = route_z_level(altura, base0, p_end)
        log_info(
            "Ruta '{}': z_ini={:.2f}, z_fin={:.2f}, z_ruta={:.2f}".format(
                g_label, base0.z, p_end.z, z_route
            )
        )
        pts = ortho_points_path(base0, p_end, altura)
        try:
            wire = create_draft_wire(pts)
            wire.Label = f"Ruta Critica hacia {toma_far.Label}"
            if hasattr(wire, "FilletRadius"):
                try:
                    wire.FilletRadius = 500.0
                except Exception as exf:
                    log_warn(f"No se pudo aplicar FilletRadius: {exf}")
            g_con = ensure_conexiones_group(doc, subg if hasattr(subg, "Group") else grupo_tomas)
            try:
                g_con.addObject(wire)
            except Exception as ex:
                log_warn(f"No se pudo mover WIRE a 'Conexiones': {ex}")
            if write_sheet and row is not None:
                set_text(hoja, f"D{row}", wire.Name)
        except Exception as ex:
            log_err(f"Error al crear WIRE: {ex}")
            if write_sheet and row is not None:
                try:
                    set_text(hoja, f"D{row}", "WIRE_ERROR")
                except Exception:
                    pass

        wrote += 1

    next_row = (base_row + wrote) if write_sheet else None
    if write_sheet and update_e1:
        bump_e1(hoja, next_row)

    if recompute:
        try:
            doc.recompute()
            log_info("Documento recomputado")
        except Exception as ex:
            log_err(f"Error en recompute: {ex}")

    return {
        "groups": len(grupos),
        "wrote": wrote,
        "base_row": base_row,
        "next_row": next_row,
        "sheet": hoja if write_sheet else None,
    }

def medir_distancia_y_dibujar_ruta():
    ts = datetime.now().strftime("%Y-%m-%d %H:%M:%S")
    log_info(f"Inicio macro RutaCritica_WIRE - version {ts}")

    doc = FreeCAD.ActiveDocument
    if doc is None:
        log_err("No hay documento activo")
        return

    sel = _selected_objects()
    if len(sel) < 2:
        log_err("Seleccione primero el objeto inicial y luego el grupo de tomas")
        return

    objeto_inicial = sel[0]
    grupo_tomas = sel[1]

    if not hasattr(objeto_inicial, "Placement"):
        log_err("El primer elemento seleccionado no tiene Placement")
        return
    if not hasattr(grupo_tomas, "Group"):
        log_err("El segundo elemento seleccionado debe ser un grupo")
        return

    altura, ok = QtGui.QInputDialog.getDouble(
        None, "Altura", "Ingrese altura Z de las rutas (mm):",
        3000, -100000, 100000, 2
    )
    if not ok:
        log_warn("Operacion cancelada por el usuario")
        return

    try:
        run_ruta_critica(
            objeto_inicial,
            grupo_tomas,
            altura,
            hoja=None,
            base_row=None,
            recompute=True,
            update_e1=True,
            write_sheet=WRITE_RESULTS_SHEET,
        )
    except Exception as ex:
        log_err(f"Fallo ejecucion: {ex}")

# Ejecutar macro
if __name__ == "__main__":
    medir_distancia_y_dibujar_ruta()

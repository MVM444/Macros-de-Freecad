# MenuText: Ordenar grupos
# Icon: Ordenar_Grupos_ElectricCR.svg

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

# Macro: Ordenar_Grupos_ElectricCR
# Descripcion: Reordena contenedores en el arbol del documento (root y grupos).
# Instrucciones clave: Seleccione grupos si usa modo Seleccion; elija Metodo; use Recursivo si desea subgrupos.
# Fecha/Hora: 2026-02-19 14:09
# Version: 1.0.0

import FreeCAD as App
import FreeCADGui as Gui
import re


def _qt_modules():
    try:
        from PySide2 import QtWidgets, QtCore
        return QtWidgets, QtCore
    except Exception:
        try:
            from PySide import QtGui as QtWidgets
            from PySide import QtCore
            return QtWidgets, QtCore
        except Exception:
            return None, None


def _msg(text):
    App.Console.PrintMessage(str(text) + "\n")


def _warn(text):
    App.Console.PrintWarning(str(text) + "\n")


def _err(text):
    App.Console.PrintError(str(text) + "\n")


def _is_body(obj):
    if obj is None:
        return False
    try:
        return obj.isDerivedFrom("PartDesign::Body")
    except Exception:
        return getattr(obj, "TypeId", "") == "PartDesign::Body"


def _is_container(obj):
    if obj is None:
        return False
    # Do not treat PartDesign Body as a container for reorder
    if _is_body(obj):
        return False
    try:
        if obj.isDerivedFrom("App::DocumentObjectGroup"):
            return True
    except Exception:
        pass
    try:
        if obj.isDerivedFrom("App::Part"):
            return True
    except Exception:
        pass
    return hasattr(obj, "Group")


def _obj_label(obj):
    try:
        label = obj.Label
    except Exception:
        label = ""
    try:
        name = obj.Name
    except Exception:
        name = ""
    return label or name or "<obj>"


def _display_name(obj):
    try:
        label = obj.Label
    except Exception:
        label = ""
    try:
        name = obj.Name
    except Exception:
        name = ""
    if label and name and label != name:
        return f"{label} [{name}]"
    return label or name or "<obj>"


def _format_obj_list(objs, limit=30):
    names = [_display_name(o) for o in objs]
    if len(names) > limit:
        return ", ".join(names[:limit]) + f", ... (+{len(names) - limit})"
    return ", ".join(names)


def _get_root_objects(doc):
    # Prefer official API if present
    if hasattr(doc, "RootObjects"):
        try:
            return list(doc.RootObjects)
        except Exception:
            pass
    if hasattr(doc, "getRootObjects"):
        try:
            return list(doc.getRootObjects())
        except Exception:
            pass
    # Fallback: filter objects with no parent group
    root = []
    for obj in list(doc.Objects):
        parent = None
        if hasattr(obj, "getParentGroup"):
            try:
                parent = obj.getParentGroup()
            except Exception:
                parent = None
        if parent:
            continue
        try:
            in_list = getattr(obj, "InList", []) or []
            if any(_is_container(p) for p in in_list):
                continue
        except Exception:
            pass
        root.append(obj)
    return root


def _sort_key_alpha(obj, use_name=False):
    if use_name:
        text = getattr(obj, "Name", "") or ""
    else:
        text = getattr(obj, "Label", "") or ""
    return text.lower()


def _sort_key_prefix(obj):
    text = getattr(obj, "Label", "") or getattr(obj, "Name", "") or ""
    m = re.match(r"^\s*(\d+)", text)
    if m:
        try:
            num = int(m.group(1))
        except Exception:
            num = 0
        return (0, num, text.lower())
    return (1, text.lower())


def _sort_objects(objs, method, use_name=False):
    if method == "manual":
        return list(objs)
    if method == "alpha":
        return sorted(objs, key=lambda o: _sort_key_alpha(o, use_name))
    if method == "prefix":
        return sorted(objs, key=_sort_key_prefix)
    return list(objs)


def _apply_manual_order(eligible, manual_names, doc):
    ordered = []
    seen = set()
    for name in manual_names or []:
        try:
            obj = doc.getObject(name)
        except Exception:
            obj = None
        if obj and obj in eligible and obj.Name not in seen:
            ordered.append(obj)
            seen.add(obj.Name)
    for obj in eligible:
        if obj.Name not in seen:
            ordered.append(obj)
            seen.add(obj.Name)
    return ordered


def _merge_subset(original, subset, pred):
    it = iter(subset)
    out = []
    for obj in original:
        if pred(obj):
            try:
                out.append(next(it))
            except StopIteration:
                out.append(obj)
        else:
            out.append(obj)
    return out


def _log_target(title, method, use_name, recursive, include_non, before, after, omitted):
    _msg("---")
    _msg(f"Target: {title}")
    _msg(f"Metodo: {method} | use_name={use_name} | recursivo={recursive} | incluir_no_contenedor={include_non}")
    _msg(f"Detectados: {len(before)}")
    _msg(f"Omitidos: {len(omitted)}")
    if omitted:
        _msg(f"Omitidos lista: {_format_obj_list(omitted)}")
    _msg(f"Antes: {_format_obj_list(before)}")
    _msg(f"Despues: {_format_obj_list(after)}")


class _ReorderDialog:
    def __init__(self, doc, parent=None):
        QtWidgets, QtCore = _qt_modules()
        if QtWidgets is None:
            raise RuntimeError("Qt no disponible")
        self.QtWidgets = QtWidgets
        self.QtCore = QtCore
        self.doc = doc
        self.manual_orders = {}
        self.targets = []
        self.target_map = {}

        self.dialog = QtWidgets.QDialog(parent)
        self.dialog.setWindowTitle("Ordenar grupos - ElectricCR")
        self.dialog.resize(640, 520)

        layout = QtWidgets.QVBoxLayout(self.dialog)

        # Options grid
        grid = QtWidgets.QGridLayout()
        layout.addLayout(grid)

        grid.addWidget(QtWidgets.QLabel("Modo"), 0, 0)
        self.mode_combo = QtWidgets.QComboBox()
        self.mode_combo.addItems(["Root", "Seleccion", "Ambos"])
        grid.addWidget(self.mode_combo, 0, 1)

        grid.addWidget(QtWidgets.QLabel("Metodo"), 1, 0)
        self.method_combo = QtWidgets.QComboBox()
        self.method_combo.addItems(["Manual", "Alfabetico", "Prefijo"])
        grid.addWidget(self.method_combo, 1, 1)

        grid.addWidget(QtWidgets.QLabel("Objetivo"), 2, 0)
        self.target_combo = QtWidgets.QComboBox()
        grid.addWidget(self.target_combo, 2, 1)

        self.recursive_cb = QtWidgets.QCheckBox("Recursivo subgrupos")
        grid.addWidget(self.recursive_cb, 0, 2)

        self.use_name_cb = QtWidgets.QCheckBox("Usar Name en vez de Label")
        grid.addWidget(self.use_name_cb, 1, 2)

        self.include_non_cb = QtWidgets.QCheckBox("Incluir no contenedores en grupos")
        grid.addWidget(self.include_non_cb, 2, 2)

        # Preview list + manual buttons
        layout.addWidget(QtWidgets.QLabel("Vista previa"))
        list_row = QtWidgets.QHBoxLayout()
        layout.addLayout(list_row)

        self.list_widget = QtWidgets.QTableWidget()
        self.list_widget.setColumnCount(2)
        self.list_widget.setHorizontalHeaderLabels(["Label", "Name"])
        self.list_widget.verticalHeader().setVisible(False)
        self.list_widget.setSelectionBehavior(QtWidgets.QAbstractItemView.SelectRows)
        self.list_widget.setSelectionMode(QtWidgets.QAbstractItemView.ExtendedSelection)
        self.list_widget.setEditTriggers(QtWidgets.QAbstractItemView.NoEditTriggers)
        self.list_widget.setAlternatingRowColors(True)
        try:
            header = self.list_widget.horizontalHeader()
            header.setStretchLastSection(True)
            header.setSectionResizeMode(0, QtWidgets.QHeaderView.Stretch)
        except Exception:
            pass
        list_row.addWidget(self.list_widget, 1)

        btn_col = QtWidgets.QVBoxLayout()
        list_row.addLayout(btn_col)
        self.btn_top = QtWidgets.QPushButton("Top")
        self.btn_up = QtWidgets.QPushButton("Subir")
        self.btn_down = QtWidgets.QPushButton("Bajar")
        self.btn_bottom = QtWidgets.QPushButton("Bottom")
        for b in (self.btn_top, self.btn_up, self.btn_down, self.btn_bottom):
            btn_col.addWidget(b)
        btn_col.addStretch(1)

        self.info_label = QtWidgets.QLabel("")
        layout.addWidget(self.info_label)

        # Apply / Cancel
        buttons = QtWidgets.QHBoxLayout()
        layout.addLayout(buttons)
        buttons.addStretch(1)
        self.apply_btn = QtWidgets.QPushButton("Aplicar")
        self.cancel_btn = QtWidgets.QPushButton("Cancelar")
        buttons.addWidget(self.apply_btn)
        buttons.addWidget(self.cancel_btn)

        # Signals
        self.mode_combo.currentIndexChanged.connect(self._on_mode_changed)
        self.method_combo.currentIndexChanged.connect(self._on_method_changed)
        self.target_combo.currentIndexChanged.connect(self._refresh_preview)
        self.recursive_cb.stateChanged.connect(self._refresh_preview)
        self.use_name_cb.stateChanged.connect(self._refresh_preview)
        self.include_non_cb.stateChanged.connect(self._refresh_preview)
        self.btn_top.clicked.connect(lambda: self._move_selected("top"))
        self.btn_bottom.clicked.connect(lambda: self._move_selected("bottom"))
        self.btn_up.clicked.connect(lambda: self._move_selected("up"))
        self.btn_down.clicked.connect(lambda: self._move_selected("down"))
        self.apply_btn.clicked.connect(self._apply)
        self.cancel_btn.clicked.connect(self.dialog.reject)

        # Init
        self._on_mode_changed()
        self._on_method_changed()

    def exec_(self):
        return self.dialog.exec_()

    def _current_method(self):
        text = self.method_combo.currentText()
        if text == "Manual":
            return "manual"
        if text == "Alfabetico":
            return "alpha"
        return "prefix"

    def _selected_groups(self):
        groups = []
        skipped = []
        try:
            sel = Gui.Selection.getSelection()
        except Exception:
            sel = []
        for obj in sel:
            if _is_container(obj):
                groups.append(obj)
            else:
                skipped.append(obj)
        return groups, skipped

    def _build_targets(self):
        self.targets = []
        self.target_map = {}
        mode = self.mode_combo.currentText()
        groups, skipped = self._selected_groups()

        if skipped:
            _warn(f"Seleccion omitida (no contenedores): {len(skipped)}")

        if mode in ("Root", "Ambos"):
            self.targets.append("root")
            self.target_map["root"] = None
        if mode in ("Seleccion", "Ambos"):
            for g in groups:
                key = g.Name
                self.targets.append(key)
                self.target_map[key] = g

        self.target_combo.blockSignals(True)
        self.target_combo.clear()
        for key in self.targets:
            if key == "root":
                self.target_combo.addItem("Root")
            else:
                obj = self.target_map.get(key)
                self.target_combo.addItem(_display_name(obj) if obj else key)
        self.target_combo.blockSignals(False)

        if not self.targets:
            self.info_label.setText("No hay grupos seleccionados.")
        else:
            self.info_label.setText("")

        self.target_combo.setEnabled(len(self.targets) > 1)

    def _on_mode_changed(self):
        self._build_targets()
        self._refresh_preview()

    def _on_method_changed(self):
        method = self._current_method()
        self.use_name_cb.setEnabled(method == "alpha")
        manual = method == "manual"
        for b in (self.btn_top, self.btn_up, self.btn_down, self.btn_bottom):
            b.setEnabled(manual)
        self._refresh_preview()

    def _current_target_key(self):
        idx = self.target_combo.currentIndex()
        if idx < 0 or idx >= len(self.targets):
            return None
        return self.targets[idx]

    def _eligible_for_target(self, key):
        if key == "root":
            root = _get_root_objects(self.doc)
            eligible = [o for o in root if _is_container(o)]
            omitted = [o for o in root if not _is_container(o)]
            return root, eligible, omitted
        obj = self.target_map.get(key)
        if not obj or not hasattr(obj, "Group"):
            return [], [], []
        original = list(getattr(obj, "Group", []) or [])
        include_non = self.include_non_cb.isChecked()
        if include_non:
            eligible = list(original)
            omitted = []
        else:
            eligible = [o for o in original if _is_container(o)]
            omitted = [o for o in original if not _is_container(o)]
        return original, eligible, omitted

    def _row_name(self, row):
        name = None
        try:
            item = self.list_widget.item(row, 0)
        except Exception:
            item = None
        if item:
            try:
                name = item.data(self.QtCore.Qt.UserRole)
            except Exception:
                name = None
        if not name:
            try:
                item2 = self.list_widget.item(row, 1)
                name = item2.text() if item2 else None
            except Exception:
                name = None
        return name

    def _selected_rows(self):
        try:
            rows = [i.row() for i in self.list_widget.selectionModel().selectedRows()]
        except Exception:
            rows = []
        return sorted(set(rows))

    def _set_list_items(self, objs, selected_names=None):
        self.list_widget.setRowCount(0)
        selected_names = set(selected_names or [])
        self.list_widget.setRowCount(len(objs))
        for row, obj in enumerate(objs):
            try:
                label = obj.Label
            except Exception:
                label = ""
            try:
                name = obj.Name
            except Exception:
                name = ""
            if not label:
                label = name
            item_label = self.QtWidgets.QTableWidgetItem(label)
            item_name = self.QtWidgets.QTableWidgetItem(name)
            try:
                item_label.setData(self.QtCore.Qt.UserRole, name)
                item_name.setData(self.QtCore.Qt.UserRole, name)
            except Exception:
                pass
            self.list_widget.setItem(row, 0, item_label)
            self.list_widget.setItem(row, 1, item_name)
            if name in selected_names:
                try:
                    self.list_widget.selectRow(row)
                except Exception:
                    item_label.setSelected(True)

    def _capture_manual_order(self):
        key = self._current_target_key()
        if not key:
            return
        if self._current_method() != "manual":
            return
        names = []
        for i in range(self.list_widget.rowCount()):
            name = self._row_name(i)
            if name:
                names.append(name)
        if names:
            self.manual_orders[key] = names

    def _refresh_preview(self):
        self._capture_manual_order()
        key = self._current_target_key()
        if not key:
            self.list_widget.setRowCount(0)
            return
        original, eligible, _omitted = self._eligible_for_target(key)
        method = self._current_method()
        if method == "manual":
            manual_names = self.manual_orders.get(key)
            if not manual_names:
                manual_names = [o.Name for o in eligible]
                self.manual_orders[key] = manual_names
            ordered = _apply_manual_order(eligible, manual_names, self.doc)
        else:
            ordered = _sort_objects(eligible, method, self.use_name_cb.isChecked())
        self._set_list_items(ordered)

    def _move_selected(self, direction):
        if self._current_method() != "manual":
            return
        count = self.list_widget.rowCount()
        if count == 0:
            return
        selected = self._selected_rows()
        if not selected:
            return
        names = [self._row_name(i) for i in range(count)]
        # Reorder names list
        if direction == "top":
            new_order = [names[i] for i in selected] + [names[i] for i in range(count) if i not in selected]
        elif direction == "bottom":
            new_order = [names[i] for i in range(count) if i not in selected] + [names[i] for i in selected]
        elif direction == "up":
            new_order = list(names)
            for i in selected:
                if i == 0:
                    continue
                if (i - 1) in selected:
                    continue
                new_order[i - 1], new_order[i] = new_order[i], new_order[i - 1]
        else:  # down
            new_order = list(names)
            for i in reversed(selected):
                if i >= count - 1:
                    continue
                if (i + 1) in selected:
                    continue
                new_order[i + 1], new_order[i] = new_order[i], new_order[i + 1]

        # Apply new order
        ordered_objs = []
        for n in new_order:
            obj = self.doc.getObject(n) if n else None
            if obj:
                ordered_objs.append(obj)
        self._set_list_items(ordered_objs, selected_names=[names[i] for i in selected if names[i]])
        self.manual_orders[self._current_target_key()] = [o.Name for o in ordered_objs]

    def _apply_root_order(self, new_root):
        # Try official API first
        if hasattr(self.doc, "reorderObjects"):
            try:
                self.doc.reorderObjects(new_root)
                return True
            except Exception:
                try:
                    self.doc.reorderObjects([o.Name for o in new_root])
                    return True
                except Exception:
                    pass
        # Try GUI API
        try:
            gdoc = Gui.ActiveDocument
        except Exception:
            gdoc = None
        if gdoc and hasattr(gdoc, "reorderObjects"):
            try:
                gdoc.reorderObjects(new_root)
                return True
            except Exception:
                try:
                    gdoc.reorderObjects([o.Name for o in new_root])
                    return True
                except Exception:
                    pass
        # Fallback: move objects to end in sequence if moveObject exists
        moved = 0
        for obj in new_root:
            if hasattr(self.doc, "moveObject"):
                try:
                    self.doc.moveObject(obj, len(self.doc.Objects))
                    moved += 1
                    continue
                except Exception:
                    try:
                        self.doc.moveObject(obj.Name, len(self.doc.Objects))
                        moved += 1
                        continue
                    except Exception:
                        pass
            if gdoc and hasattr(gdoc, "moveObject"):
                try:
                    gdoc.moveObject(obj, len(self.doc.Objects))
                    moved += 1
                    continue
                except Exception:
                    try:
                        gdoc.moveObject(obj.Name, len(self.doc.Objects))
                        moved += 1
                        continue
                    except Exception:
                        pass
        if moved:
            _warn("Fallback usado: moveObject para ordenar root")
            return True
        _warn("No se pudo reordenar root: API no disponible")
        return False

    def _apply_group_order(self, group_obj, ordered, include_non):
        try:
            if include_non:
                group_obj.Group = ordered
            else:
                original = list(getattr(group_obj, "Group", []) or [])
                merged = _merge_subset(original, ordered, _is_container)
                group_obj.Group = merged
            return True
        except Exception as e:
            _err(f"Error reordenando grupo {group_obj.Name}: {e}")
            return False

    def _apply_recursive(self, group_obj, method, use_name, include_non, visited):
        if group_obj is None:
            return
        if group_obj.Name in visited:
            return
        visited.add(group_obj.Name)
        # Skip PartDesign Body internal order
        if _is_body(group_obj):
            return
        try:
            children = list(getattr(group_obj, "Group", []) or [])
        except Exception:
            children = []
        for child in children:
            if not _is_container(child):
                continue
            # Reorder child group
            original = list(getattr(child, "Group", []) or [])
            if include_non:
                eligible = list(original)
                omitted = []
            else:
                eligible = [o for o in original if _is_container(o)]
                omitted = [o for o in original if not _is_container(o)]
            if method == "manual":
                ordered = list(eligible)
            else:
                ordered = _sort_objects(eligible, method, use_name)
            _log_target(f"Group(rec) {child.Name}", method, use_name, True, include_non, eligible, ordered, omitted)
            self._apply_group_order(child, ordered, include_non)
            self._apply_recursive(child, method, use_name, include_non, visited)

    def _apply(self):
        self._capture_manual_order()
        method = self._current_method()
        use_name = self.use_name_cb.isChecked()
        recursive = self.recursive_cb.isChecked()
        include_non = self.include_non_cb.isChecked()

        if not self.doc:
            _err("No hay documento activo")
            return

        # Recompute targets at apply time
        self._build_targets()
        if not self.targets:
            _warn("No hay objetivos para reordenar")
            return

        trans_open = False
        try:
            self.doc.openTransaction("ElectricCR: ordenar grupos")
            trans_open = True
        except Exception:
            trans_open = False

        try:
            # Apply per target
            for key in self.targets:
                if key == "root":
                    root_all, eligible, omitted = self._eligible_for_target("root")
                    if not eligible:
                        _warn("Root sin contenedores para ordenar")
                        continue
                    if method == "manual":
                        ordered = _apply_manual_order(eligible, self.manual_orders.get("root", []), self.doc)
                    else:
                        ordered = _sort_objects(eligible, method, use_name)
                    # Merge into full root order to keep non containers in place
                    new_root = _merge_subset(root_all, ordered, _is_container)
                    _log_target("Root", method, use_name, recursive, False, eligible, ordered, omitted)
                    self._apply_root_order(new_root)
                else:
                    group_obj = self.target_map.get(key)
                    if not group_obj:
                        continue
                    if _is_body(group_obj):
                        _warn(f"Omitido Body: {group_obj.Name}")
                        continue
                    original, eligible, omitted = self._eligible_for_target(key)
                    if method == "manual":
                        ordered = _apply_manual_order(eligible, self.manual_orders.get(key, []), self.doc)
                    else:
                        ordered = _sort_objects(eligible, method, use_name)
                    _log_target(f"Group {group_obj.Name}", method, use_name, recursive, include_non, eligible, ordered, omitted)
                    self._apply_group_order(group_obj, ordered, include_non)
                    if recursive:
                        self._apply_recursive(group_obj, method, use_name, include_non, set())

            try:
                self.doc.recompute()
            except Exception:
                pass

            if trans_open:
                try:
                    self.doc.commitTransaction()
                except Exception:
                    pass

            self.dialog.accept()
        except Exception as e:
            if trans_open:
                try:
                    self.doc.abortTransaction()
                except Exception:
                    pass
            _err(f"Error aplicando orden: {e}")


def run():
    doc = App.ActiveDocument
    if doc is None:
        _err("No hay documento activo")
        return
    QtWidgets, _QtCore = _qt_modules()
    if QtWidgets is None:
        _err("Qt no disponible")
        return
    try:
        parent = Gui.getMainWindow()
    except Exception:
        parent = None
    dlg = _ReorderDialog(doc, parent)
    dlg.exec_()


if __name__ == "__main__":
    run()

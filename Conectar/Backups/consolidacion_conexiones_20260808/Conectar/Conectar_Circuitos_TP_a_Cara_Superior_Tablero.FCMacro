# -*- coding: utf-8 -*-
# MenuText: Conectar Circuitos TP a Cara Superior del Tablero...
# Icon: Conectar/Conectar_Circuitos_TP_a_Cara_Superior_Tablero.svg

"""
Conecta los circuitos TP existentes con la cara superior real del tablero TP.

- Detecta el tablero por Codigo == "TP".
- Detecta una cara horizontal perteneciente al Shape del tablero, en Z maxima.
- Reserva 18 ranuras (TP-001 a TP-018) dentro de esa cara.
- Elige como origen la caja octogonal mas cercana al tablero de cada circuito.
- Lleva las rutas sobre los muros y baja hasta la cara superior del tablero.
- Actualiza objetos generados previamente en vez de duplicarlos.
"""

import json
import math
import re

import FreeCAD as App
import Part

try:
    import FreeCADGui as Gui
    GUI_UP = True
except Exception:
    Gui = None
    GUI_UP = False

QtWidgets = QtCore = None
for _binding in ("PySide6", "PySide2"):
    try:
        _qt = __import__(_binding, fromlist=["QtWidgets", "QtCore"])
        QtWidgets, QtCore = _qt.QtWidgets, _qt.QtCore
        break
    except Exception:
        pass
if QtWidgets is None:
    try:
        from PySide import QtGui as QtWidgets  # type: ignore
        from PySide import QtCore  # type: ignore
    except Exception:
        pass


TAG = "[TP_A_TABLERO_TOP]"
GENERATED_BY = "Conectar_Circuitos_TP_a_Cara_Superior_Tablero"
PARAM_PATH = "User parameter:BaseApp/Preferences/Mod/ElectricCR/TPaTableroTop"
DEFAULT_ROUTE_Z = 3300.0
DEFAULT_LANE_SPACING = 50.0
DEFAULT_APPROACH_CLEARANCE = 300.0
DEFAULT_BEND_RADIUS = 100.0
DEFAULT_PORT_STUB = 80.0
MAX_TP_CIRCUITS = 18
SLOT_ROWS = 2
SLOT_COLUMNS = 9
EPS = 1e-7


def _log(message):
    App.Console.PrintMessage(TAG + " " + str(message) + "\n")


def _warn(message):
    App.Console.PrintWarning(TAG + " " + str(message) + "\n")


def _err(message):
    App.Console.PrintError(TAG + " " + str(message) + "\n")


def _safe(value):
    try:
        return str(value or "")
    except Exception:
        return ""


def _is_group(obj):
    return obj is not None and hasattr(obj, "Group")


def _walk_group(group, seen=None):
    if seen is None:
        seen = set()
    if group is None or group.Name in seen:
        return []
    seen.add(group.Name)
    out = []
    for child in list(getattr(group, "Group", []) or []):
        out.append(child)
        if _is_group(child):
            out.extend(_walk_group(child, seen))
    return out


def _ensure_property(obj, ptype, name, group, description):
    if name not in getattr(obj, "PropertiesList", []):
        obj.addProperty(ptype, name, group, description)


def _unique_name(doc, prefix):
    if doc.getObject(prefix) is None:
        return prefix
    index = 1
    while doc.getObject(prefix + "_%03d" % index) is not None:
        index += 1
    return prefix + "_%03d" % index


def _ensure_child_group(doc, parent, label):
    for child in list(getattr(parent, "Group", []) or []):
        if _is_group(child) and _safe(getattr(child, "Label", "")) == label:
            return child
    token = re.sub(r"[^0-9A-Za-z_]+", "_", label).strip("_") or "Alimentadores_TP"
    group = doc.addObject("App::DocumentObjectGroup", _unique_name(doc, "Grupo_" + token))
    group.Label = label
    _ensure_property(group, "App::PropertyString", "GeneradoPor", "ElectricCR", "Generador")
    group.GeneradoPor = GENERATED_BY
    parent.addObject(group)
    return group


def _move_to_feeder_group(doc, obj, target_group):
    for parent in list(getattr(obj, "InList", []) or []):
        if parent is target_group or not _is_group(parent):
            continue
        name = _safe(getattr(parent, "Name", ""))
        generated = _safe(getattr(parent, "GeneradoPor", "")) == GENERATED_BY
        legacy_this_run = name.startswith("Alimentadores_TP")
        if generated or legacy_this_run:
            try:
                parent.removeObject(obj)
            except Exception:
                pass
    target_group.addObject(obj)


def _cleanup_empty_feeder_groups(doc):
    removable = []
    for group in list(doc.Objects):
        if not _is_group(group) or list(getattr(group, "Group", []) or []):
            continue
        name = _safe(getattr(group, "Name", ""))
        generated = _safe(getattr(group, "GeneradoPor", "")) == GENERATED_BY
        legacy_this_run = name.startswith("Alimentadores_TP")
        if generated or legacy_this_run:
            removable.append(group)
    for group in removable:
        try:
            doc.removeObject(group.Name)
        except Exception:
            pass


def _selected_objects():
    if not GUI_UP:
        return []
    try:
        return list(Gui.Selection.getSelection() or [])
    except Exception:
        return []


def _is_tp_panel(obj):
    if obj is None or _is_group(obj):
        return False
    if _safe(getattr(obj, "Codigo", "")).strip().upper() == "TP":
        return True
    text = (_safe(getattr(obj, "Label", "")) + " " + _safe(getattr(obj, "Name", ""))).upper()
    return "TP - PRINCIPAL" in text


def _find_tp_panel(doc):
    selected = [obj for obj in _selected_objects() if _is_tp_panel(obj)]
    candidates = selected or [obj for obj in doc.Objects if _is_tp_panel(obj)]
    unique = []
    seen = set()
    for obj in candidates:
        if obj.Name not in seen:
            unique.append(obj)
            seen.add(obj.Name)
    if len(unique) != 1:
        raise RuntimeError("Se esperaba un unico tablero TP; encontrados: %d" % len(unique))
    return unique[0]


def _face_mid_parameter(face):
    umin, umax, vmin, vmax = face.ParameterRange
    return 0.5 * (umin + umax), 0.5 * (vmin + vmax)


def _top_face_from_panel(panel):
    shape = getattr(panel, "Shape", None)
    if shape is None or shape.isNull():
        raise RuntimeError("El tablero TP no tiene Shape utilizable.")
    board_top = float(shape.BoundBox.ZMax)
    candidates = []
    for index, face in enumerate(shape.Faces, start=1):
        try:
            u, v = _face_mid_parameter(face)
            normal = face.normalAt(u, v)
            center = face.valueAt(u, v)
            bb = face.BoundBox
        except Exception:
            continue
        if float(normal.z) < 0.70:
            continue
        if abs(float(bb.ZMax) - float(bb.ZMin)) > 0.1:
            continue
        if abs(float(center.z) - board_top) > 0.5:
            continue
        candidates.append((float(face.Area), index, face, center, normal))
    if not candidates:
        raise RuntimeError("No se encontro una cara superior horizontal real en el tablero TP.")
    candidates.sort(key=lambda item: item[0], reverse=True)
    _area, index, face, center, normal = candidates[0]
    return index, face, center, normal


def _circuit_number_from_label(label):
    match = re.match(r"^\s*TP\s*[-_]\s*0*(\d+)\b", _safe(label), flags=re.IGNORECASE)
    if not match:
        return None
    number = int(match.group(1))
    return number if 1 <= number <= MAX_TP_CIRCUITS else None


def _is_real_octagonal_box(obj):
    if obj is None or _is_group(obj):
        return False
    text = (_safe(getattr(obj, "Name", "")) + " " + _safe(getattr(obj, "Label", ""))).lower()
    if any(token in text for token in ("master", "template", "plantilla", "prototype")):
        return False
    if _safe(getattr(obj, "Tipo", "")) == "EMT_Octagon_Box":
        return True
    return "PuertosJSON" in getattr(obj, "PropertiesList", []) and "octogonal" in text


def _boxes_in_circuit(group):
    out = []
    seen = set()
    try:
        for obj in list(getattr(group, "CajasOctogonalesAsignadas", []) or []):
            if _is_real_octagonal_box(obj) and obj.Name not in seen:
                out.append(obj)
                seen.add(obj.Name)
    except Exception:
        pass
    for obj in _walk_group(group):
        if _is_real_octagonal_box(obj) and obj.Name not in seen:
            out.append(obj)
            seen.add(obj.Name)
    return out


def _find_circuit_groups(doc):
    by_number = {}
    for obj in doc.Objects:
        if not _is_group(obj):
            continue
        number = _circuit_number_from_label(getattr(obj, "Label", ""))
        if number is None:
            continue
        boxes = _boxes_in_circuit(obj)
        if not boxes:
            continue
        current = by_number.get(number)
        if current is None or len(boxes) > len(current[1]):
            by_number[number] = (obj, boxes)
    return by_number


def _vector_length_xy(vector):
    return math.hypot(float(vector.x), float(vector.y))


def _normalize_xy(vector):
    length = _vector_length_xy(vector)
    if length <= EPS:
        return App.Vector(1.0, 0.0, 0.0)
    return App.Vector(float(vector.x) / length, float(vector.y) / length, 0.0)


def _box_ports_world(box):
    raw = _safe(getattr(box, "PuertosJSON", "")).strip()
    if not raw:
        return []
    try:
        items = json.loads(raw)
    except Exception:
        return []
    out = []
    for item in items if isinstance(items, list) else []:
        if not isinstance(item, dict):
            continue
        position = item.get("position")
        direction = item.get("direction")
        if not isinstance(position, list) or len(position) != 3:
            continue
        try:
            local_point = App.Vector(float(position[0]), float(position[1]), float(position[2]))
            world_point = box.Placement.multVec(local_point)
            if isinstance(direction, list) and len(direction) == 3:
                local_dir = App.Vector(float(direction[0]), float(direction[1]), float(direction[2]))
                world_dir = box.Placement.Rotation.multVec(local_dir)
            else:
                world_dir = App.Vector(0.0, 0.0, 0.0)
        except Exception:
            continue
        out.append({"name": _safe(item.get("name", "")), "point": world_point, "dir": world_dir})
    return out


def _source_port_toward_panel(box, panel_center):
    ports = [p for p in _box_ports_world(box) if p["name"].lower() != "bottom"]
    if not ports:
        bb = box.Shape.BoundBox
        point = App.Vector(bb.Center.x, bb.Center.y, bb.ZMax)
        direction = _normalize_xy(panel_center - point)
        return point, direction, "Superior"

    def score(port):
        toward = _normalize_xy(panel_center - port["point"])
        direction = _normalize_xy(port["dir"])
        alignment = float(direction.dot(toward))
        distance = _vector_length_xy(panel_center - port["point"])
        return (-alignment, distance)

    chosen = sorted(ports, key=score)[0]
    return chosen["point"], _normalize_xy(chosen["dir"]), chosen["name"]


def _nearest_source_box(boxes, panel_center):
    return min(boxes, key=lambda box: _vector_length_xy(box.Shape.BoundBox.Center - panel_center))


def _slot_point_on_face(face, circuit_number):
    index = int(circuit_number) - 1
    row = index // SLOT_COLUMNS
    column = index % SLOT_COLUMNS
    umin, umax, vmin, vmax = face.ParameterRange
    u = umin + ((row + 1.0) / (SLOT_ROWS + 1.0)) * (umax - umin)
    v = vmin + ((column + 1.0) / (SLOT_COLUMNS + 1.0)) * (vmax - vmin)
    point = face.valueAt(u, v)
    distance = float(face.distToShape(Part.Vertex(point))[0])
    if distance > 0.01:
        raise RuntimeError("La ranura TP-%03d no pertenece a la cara superior." % circuit_number)
    return point


def _route_side(source, board_bb):
    center = board_bb.Center
    dx = float(source.x - center.x)
    dy = float(source.y - center.y)
    if abs(dy) >= abs(dx):
        return "North" if dy >= 0.0 else "South"
    return "East" if dx >= 0.0 else "West"


def _dedupe(points, tolerance=0.01):
    out = []
    for point in points:
        p = App.Vector(point)
        if not out or out[-1].distanceToPoint(p) > tolerance:
            out.append(p)
    return out


def _simplify_collinear(points, tolerance=0.01):
    pts = _dedupe(points, tolerance)
    if len(pts) < 3:
        return pts
    out = [pts[0]]
    for index in range(1, len(pts) - 1):
        a, b, c = out[-1], pts[index], pts[index + 1]
        v1, v2 = b - a, c - b
        l1, l2 = v1.Length, v2.Length
        if l1 <= tolerance or l2 <= tolerance:
            continue
        cross = v1.cross(v2).Length
        if cross <= tolerance * l1 * l2 and float(v1.dot(v2)) > 0.0:
            continue
        out.append(b)
    out.append(pts[-1])
    return out


def _rounded_wire(points, radius):
    pts = _simplify_collinear(points)
    if len(pts) < 2:
        raise RuntimeError("Ruta con menos de dos puntos.")
    if len(pts) == 2 or radius <= 0.1:
        return Part.makePolygon(pts)

    edges = []
    cursor = pts[0]
    for index in range(1, len(pts) - 1):
        a, b, c = pts[index - 1], pts[index], pts[index + 1]
        incoming, outgoing = b - a, c - b
        len_in, len_out = incoming.Length, outgoing.Length
        if len_in <= EPS or len_out <= EPS:
            continue
        vin, vout = incoming / len_in, outgoing / len_out
        dot = float(vin.dot(vout))
        if abs(dot) > 0.999:
            if cursor.distanceToPoint(b) > EPS:
                edges.append(Part.makeLine(cursor, b))
            cursor = b
            continue
        cut = min(float(radius), 0.35 * len_in, 0.35 * len_out)
        if cut <= 0.5:
            if cursor.distanceToPoint(b) > EPS:
                edges.append(Part.makeLine(cursor, b))
            cursor = b
            continue
        q1 = b - vin * cut
        q2 = b + vout * cut
        if cursor.distanceToPoint(q1) > EPS:
            edges.append(Part.makeLine(cursor, q1))
        center = b - vin * cut + vout * cut
        radial = (q1 - center) + (q2 - center)
        if radial.Length <= EPS:
            edges.append(Part.makeLine(q1, q2))
        else:
            midpoint = center + radial / radial.Length * cut
            edges.append(Part.Arc(q1, midpoint, q2).toShape())
        cursor = q2
    if cursor.distanceToPoint(pts[-1]) > EPS:
        edges.append(Part.makeLine(cursor, pts[-1]))
    try:
        return Part.Wire(edges)
    except Exception:
        return Part.makePolygon(pts)


def _route_points(job, rank, cfg, board_bb):
    source = job["source_point"]
    direction = job["source_direction"]
    destination = job["destination"]
    route_z = max(float(cfg["route_z"]), float(source.z) + 50.0)
    stub = float(cfg["port_stub"])
    spacing = float(cfg["lane_spacing"])
    clearance = float(cfg["approach_clearance"])
    p0 = App.Vector(source)
    p1 = App.Vector(source.x + direction.x * stub, source.y + direction.y * stub, source.z)
    p2 = App.Vector(p1.x, p1.y, route_z)
    side = job["side"]
    offset = clearance + rank * spacing
    if side == "North":
        lane = float(board_bb.YMax) + offset
        p3 = App.Vector(p2.x, lane, route_z)
        p4 = App.Vector(destination.x, lane, route_z)
        p5 = App.Vector(destination.x, destination.y, route_z)
    elif side == "South":
        lane = float(board_bb.YMin) - offset
        p3 = App.Vector(p2.x, lane, route_z)
        p4 = App.Vector(destination.x, lane, route_z)
        p5 = App.Vector(destination.x, destination.y, route_z)
    elif side == "East":
        lane = float(board_bb.XMax) + offset
        p3 = App.Vector(lane, p2.y, route_z)
        p4 = App.Vector(lane, destination.y, route_z)
        p5 = App.Vector(destination.x, destination.y, route_z)
    else:
        lane = float(board_bb.XMin) - offset
        p3 = App.Vector(lane, p2.y, route_z)
        p4 = App.Vector(lane, destination.y, route_z)
        p5 = App.Vector(destination.x, destination.y, route_z)
    p6 = App.Vector(destination)
    return _simplify_collinear([p0, p1, p2, p3, p4, p5, p6])


def _find_existing_feeder(doc, circuit_id):
    matches = []
    for obj in doc.Objects:
        if _safe(getattr(obj, "GeneradoPor", "")) != GENERATED_BY:
            continue
        if _safe(getattr(obj, "CircuitoID", "")) == circuit_id:
            matches.append(obj)
    return matches[0] if matches else None


def _style_feeder(obj):
    view = getattr(obj, "ViewObject", None)
    if view is None:
        return
    try:
        view.LineColor = (1.0, 0.25, 0.05)
        view.PointColor = (1.0, 0.25, 0.05)
        view.ShapeColor = (1.0, 0.25, 0.05)
        view.LineWidth = 3.5
    except Exception:
        pass


def _write_feeder(doc, job, route_points, shape, panel, face_index, cfg):
    circuit_id = job["circuit_id"]
    obj = _find_existing_feeder(doc, circuit_id)
    created = obj is None
    if obj is None:
        obj = doc.addObject("Part::Feature", _unique_name(doc, "Alimentador_" + circuit_id.replace("-", "_")))
    obj.Label = "Alimentador %s -> TP (Top)" % circuit_id
    obj.Shape = shape

    _ensure_property(obj, "App::PropertyString", "GeneradoPor", "ElectricCR", "Generador")
    _ensure_property(obj, "App::PropertyString", "CircuitoID", "ElectricCR", "Circuito")
    _ensure_property(obj, "App::PropertyString", "CaraTablero", "Tablero", "Cara de llegada")
    _ensure_property(obj, "App::PropertyInteger", "FaceIndexTablero", "Tablero", "Indice de cara")
    _ensure_property(obj, "App::PropertyInteger", "SlotTablero", "Tablero", "Ranura TP")
    _ensure_property(obj, "App::PropertyBool", "EsCaraRealTablero", "Tablero", "Destino pertenece al Shape")
    _ensure_property(obj, "App::PropertyLink", "CajaOrigen", "Vinculos", "Caja octogonal de origen")
    _ensure_property(obj, "App::PropertyLink", "TableroDestino", "Vinculos", "Tablero de destino")
    _ensure_property(obj, "App::PropertyString", "PuertoOrigen", "Puertos", "Puerto de caja")
    _ensure_property(obj, "App::PropertyVector", "PuntoOrigen", "Puertos", "Punto inicial")
    _ensure_property(obj, "App::PropertyVector", "PuntoDestino", "Puertos", "Punto en cara superior")
    _ensure_property(obj, "App::PropertyFloat", "AlturaRuta", "Ruta", "Cota de distribucion")
    _ensure_property(obj, "App::PropertyString", "RutaJSON", "Ruta", "Puntos mundiales")
    _ensure_property(obj, "App::PropertyString", "EstadoConexion", "Ruta", "Estado")

    obj.GeneradoPor = GENERATED_BY
    obj.CircuitoID = circuit_id
    obj.CaraTablero = "Top"
    obj.FaceIndexTablero = int(face_index)
    obj.SlotTablero = int(job["number"])
    obj.EsCaraRealTablero = True
    obj.CajaOrigen = job["source_box"]
    obj.TableroDestino = panel
    obj.PuertoOrigen = job["source_port_name"]
    obj.PuntoOrigen = App.Vector(job["source_point"])
    obj.PuntoDestino = App.Vector(job["destination"])
    obj.AlturaRuta = float(cfg["route_z"])
    obj.RutaJSON = json.dumps([[p.x, p.y, p.z] for p in route_points], separators=(",", ":"))
    obj.EstadoConexion = "Conectado"
    _style_feeder(obj)

    group = _ensure_child_group(doc, job["circuit_group"], "Alimentadores " + circuit_id)
    try:
        _move_to_feeder_group(doc, obj, group)
    except Exception:
        pass
    return obj, created


def _default_cfg():
    p = App.ParamGet(PARAM_PATH)
    return {
        "route_z": float(p.GetFloat("route_z", DEFAULT_ROUTE_Z)),
        "lane_spacing": float(p.GetFloat("lane_spacing", DEFAULT_LANE_SPACING)),
        "approach_clearance": float(p.GetFloat("approach_clearance", DEFAULT_APPROACH_CLEARANCE)),
        "bend_radius": float(p.GetFloat("bend_radius", DEFAULT_BEND_RADIUS)),
        "port_stub": float(p.GetFloat("port_stub", DEFAULT_PORT_STUB)),
    }


def _save_cfg(cfg):
    p = App.ParamGet(PARAM_PATH)
    for key in ("route_z", "lane_spacing", "approach_clearance", "bend_radius", "port_stub"):
        p.SetFloat(key, float(cfg[key]))


def _run_dialog(panel, face_index, face, circuit_numbers):
    cfg = _default_cfg()
    if (not GUI_UP) or QtWidgets is None:
        return cfg
    missing = [number for number in range(1, MAX_TP_CIRCUITS + 1) if number not in circuit_numbers]
    dlg = QtWidgets.QDialog(Gui.getMainWindow())
    dlg.setWindowTitle("Circuitos TP a cara superior del tablero")
    dlg.setMinimumWidth(570)
    info = QtWidgets.QLabel(
        "Tablero: {}\nCara real: Face{} | Z={:.1f} mm\nCircuitos encontrados: {}\nFaltantes/reservados: {}".format(
            panel.Label,
            face_index,
            face.BoundBox.ZMax,
            ", ".join("TP-%03d" % n for n in circuit_numbers),
            ", ".join("TP-%03d" % n for n in missing) or "ninguno",
        )
    )
    info.setWordWrap(True)
    controls = {}
    specifications = [
        ("route_z", "Altura de rutas:", 3001.0, 10000.0, " mm"),
        ("lane_spacing", "Separacion de carriles:", 10.0, 500.0, " mm"),
        ("approach_clearance", "Separacion al tablero:", 50.0, 3000.0, " mm"),
        ("bend_radius", "Radio de curvas:", 0.0, 1000.0, " mm"),
        ("port_stub", "Salida recta desde caja:", 10.0, 500.0, " mm"),
    ]
    form = QtWidgets.QFormLayout()
    for key, label, minimum, maximum, suffix in specifications:
        spin = QtWidgets.QDoubleSpinBox()
        spin.setRange(minimum, maximum)
        spin.setDecimals(1)
        spin.setSuffix(suffix)
        spin.setValue(float(cfg[key]))
        controls[key] = spin
        form.addRow(label, spin)
    buttons = QtWidgets.QDialogButtonBox(QtWidgets.QDialogButtonBox.Ok | QtWidgets.QDialogButtonBox.Cancel)
    buttons.accepted.connect(dlg.accept)
    buttons.rejected.connect(dlg.reject)
    layout = QtWidgets.QVBoxLayout(dlg)
    layout.addWidget(info)
    layout.addLayout(form)
    layout.addWidget(buttons)
    execute = getattr(dlg, "exec", None) or getattr(dlg, "exec_", None)
    if execute() != QtWidgets.QDialog.Accepted:
        return None
    for key, control in controls.items():
        cfg[key] = float(control.value())
    _save_cfg(cfg)
    return cfg


def main(doc_override=None, cfg_override=None):
    doc = doc_override or App.ActiveDocument
    if doc is None:
        _err("No hay documento activo.")
        return None
    try:
        panel = _find_tp_panel(doc)
        face_index, top_face, panel_center, _normal = _top_face_from_panel(panel)
    except Exception as exc:
        _err(exc)
        return None

    circuit_map = _find_circuit_groups(doc)
    requested_ids = set()
    if cfg_override is not None:
        for value in list(cfg_override.get("circuit_ids", []) or []):
            number = _circuit_number_from_label(_safe(value))
            if number is not None:
                requested_ids.add(number)
    if requested_ids:
        circuit_map = {number: data for number, data in circuit_map.items() if number in requested_ids}
    circuit_numbers = sorted(circuit_map)
    if not circuit_numbers:
        _warn("No se encontraron circuitos TP con cajas octogonales.")
        return None
    cfg = dict(cfg_override) if cfg_override is not None else _run_dialog(panel, face_index, top_face, circuit_numbers)
    if cfg is None:
        _warn("Operacion cancelada.")
        return None
    for key, fallback in (
        ("route_z", DEFAULT_ROUTE_Z),
        ("lane_spacing", DEFAULT_LANE_SPACING),
        ("approach_clearance", DEFAULT_APPROACH_CLEARANCE),
        ("bend_radius", DEFAULT_BEND_RADIUS),
        ("port_stub", DEFAULT_PORT_STUB),
    ):
        cfg[key] = float(cfg.get(key, fallback))
    cfg["route_z"] = max(3001.0, cfg["route_z"])

    jobs = []
    for number in circuit_numbers:
        group, boxes = circuit_map[number]
        source_box = _nearest_source_box(boxes, panel_center)
        source_point, source_direction, port_name = _source_port_toward_panel(source_box, panel_center)
        destination = _slot_point_on_face(top_face, number)
        jobs.append(
            {
                "number": number,
                "circuit_id": "TP-%03d" % number,
                "circuit_group": group,
                "source_box": source_box,
                "source_point": source_point,
                "source_direction": source_direction,
                "source_port_name": port_name,
                "destination": destination,
                "side": _route_side(source_point, panel.Shape.BoundBox),
            }
        )

    side_groups = {}
    for job in jobs:
        side_groups.setdefault(job["side"], []).append(job)
    for side_jobs in side_groups.values():
        side_jobs.sort(key=lambda job: job["number"])

    created = updated = 0
    feeders = []
    doc.openTransaction("ElectricCR: conectar circuitos TP a cara superior")
    try:
        for side, side_jobs in side_groups.items():
            for rank, job in enumerate(side_jobs):
                points = _route_points(job, rank, cfg, panel.Shape.BoundBox)
                shape = _rounded_wire(points, cfg["bend_radius"])
                feeder, was_created = _write_feeder(doc, job, points, shape, panel, face_index, cfg)
                feeders.append(feeder)
                created += 1 if was_created else 0
                updated += 0 if was_created else 1
                _log(
                    "{} | caja={} | puerto={} | lado={} | destino=({:.1f},{:.1f},{:.1f})".format(
                        job["circuit_id"],
                        job["source_box"].Label,
                        job["source_port_name"],
                        side,
                        job["destination"].x,
                        job["destination"].y,
                        job["destination"].z,
                    )
                )
        _cleanup_empty_feeder_groups(doc)
        doc.recompute()
        doc.commitTransaction()
    except Exception as exc:
        try:
            doc.abortTransaction()
        except Exception:
            pass
        _err("Fallo general: " + str(exc))
        return None

    missing = [number for number in range(1, MAX_TP_CIRCUITS + 1) if number not in circuit_numbers]
    result = {
        "tablero": panel.Name,
        "cara": face_index,
        "cara_z": float(top_face.BoundBox.ZMax),
        "circuitos": len(feeders),
        "creados": created,
        "actualizados": updated,
        "faltantes": ["TP-%03d" % number for number in missing],
    }
    _log("Finalizado: " + json.dumps(result, ensure_ascii=False))
    return result


if __name__ == "__main__":
    main()

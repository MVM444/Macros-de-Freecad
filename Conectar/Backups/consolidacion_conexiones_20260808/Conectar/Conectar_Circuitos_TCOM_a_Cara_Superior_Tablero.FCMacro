# -*- coding: utf-8 -*-
# MenuText: Conectar Circuitos TCOM a Cara Superior del Tablero...
# Icon: Conectar/Conectar_Circuitos_TCOM_a_Cara_Superior_Tablero.svg

"""Alimentadores de TCOM-01..TCOM-05 hacia la cara superior real del tablero TCOM."""

from pathlib import Path
import json
import re

import FreeCAD as App
import Part


TAG = "[TCOM_A_TABLERO_TOP]"
GENERATED_BY = "Conectar_Circuitos_TCOM_a_Cara_Superior_Tablero"
HELPER_MACRO = "Conectar_Circuitos_TP_a_Cara_Superior_Tablero.FCMacro"
PARAM_PATH = "User parameter:BaseApp/Preferences/Mod/ElectricCR/TCOMaTableroTop"
DEFAULT_ROUTE_Z = 3400.0
DEFAULT_LANE_SPACING = 50.0
DEFAULT_APPROACH_CLEARANCE = 300.0
DEFAULT_BEND_RADIUS = 100.0
DEFAULT_PORT_STUB = 80.0
MAX_CIRCUITS = 5


def _load_helpers():
    path = Path(__file__).resolve().with_name(HELPER_MACRO)
    if not path.exists():
        raise RuntimeError("No se encontro la macro auxiliar: " + str(path))
    source = path.read_text(encoding="utf-8-sig")
    source = re.sub(
        r"\nif\s+__name__\s*==\s*[\"']__main__[\"']\s*:\s*\n\s*main\(\)\s*\Z",
        "\n",
        source,
        flags=re.MULTILINE,
    )
    namespace = {"__name__": "_electriccr_tp_top_helpers_tcom", "__file__": str(path)}
    exec(compile(source, str(path), "exec"), namespace, namespace)
    return namespace


_H = _load_helpers()
Gui = _H.get("Gui")
GUI_UP = bool(_H.get("GUI_UP", False))
QtWidgets = _H.get("QtWidgets")


def _log(message):
    App.Console.PrintMessage(TAG + " " + str(message) + "\n")


def _warn(message):
    App.Console.PrintWarning(TAG + " " + str(message) + "\n")


def _err(message):
    App.Console.PrintError(TAG + " " + str(message) + "\n")


def _safe(value):
    try:
        return str(value or "")
    except Exception:
        return ""


def _ensure_property(obj, ptype, name, group, description):
    if name not in getattr(obj, "PropertiesList", []):
        obj.addProperty(ptype, name, group, description)


def _is_tcom_panel(obj):
    if obj is None or hasattr(obj, "Group"):
        return False
    if _safe(getattr(obj, "Codigo", "")).strip().upper() == "TCOM":
        return True
    return _safe(getattr(obj, "Label", "")).strip().upper().startswith("TCOM -")


def _find_tcom_panel(doc):
    selected = []
    if GUI_UP:
        try:
            selected = [obj for obj in Gui.Selection.getSelection() if _is_tcom_panel(obj)]
        except Exception:
            pass
    candidates = selected or [obj for obj in doc.Objects if _is_tcom_panel(obj)]
    unique = {obj.Name: obj for obj in candidates}
    if len(unique) != 1:
        raise RuntimeError("Se esperaba un unico tablero TCOM; encontrados: %d" % len(unique))
    return list(unique.values())[0]


def _circuit_number(label):
    match = re.match(r"^\s*TCOM\s*[-_]\s*0*(\d+)\b", _safe(label), flags=re.IGNORECASE)
    if not match:
        return None
    number = int(match.group(1))
    return number if 1 <= number <= MAX_CIRCUITS else None


def _box_mentions_circuit(box, circuit_id):
    try:
        values = json.loads(_safe(getattr(box, "CircuitosJSON", "[]")))
    except Exception:
        return False
    return isinstance(values, list) and any(_safe(value).startswith(circuit_id) for value in values)


def _find_circuit_groups(doc):
    all_boxes = [obj for obj in doc.Objects if _H["_is_real_octagonal_box"](obj)]
    result = {}
    for group in doc.Objects:
        if not hasattr(group, "Group"):
            continue
        number = _circuit_number(getattr(group, "Label", ""))
        if number is None:
            continue
        circuit_id = "TCOM-%02d" % number
        direct = [obj for obj in _H["_walk_group"](group) if _H["_is_real_octagonal_box"](obj)]
        metadata = [box for box in all_boxes if _box_mentions_circuit(box, circuit_id)]
        boxes = list({box.Name: box for box in direct + metadata}.values())
        if boxes:
            result[number] = (group, boxes)
    return result


def _slot_point_on_face(face, circuit_number):
    umin, umax, vmin, vmax = face.ParameterRange
    umid, vmid = 0.5 * (umin + umax), 0.5 * (vmin + vmax)
    pu0 = face.valueAt(umin + 0.1 * (umax - umin), vmid)
    pu1 = face.valueAt(umin + 0.9 * (umax - umin), vmid)
    pv0 = face.valueAt(umid, vmin + 0.1 * (vmax - vmin))
    pv1 = face.valueAt(umid, vmin + 0.9 * (vmax - vmin))
    fraction = float(circuit_number) / float(MAX_CIRCUITS + 1)
    if pu0.distanceToPoint(pu1) >= pv0.distanceToPoint(pv1):
        u, v = umin + fraction * (umax - umin), vmid
    else:
        u, v = umid, vmin + fraction * (vmax - vmin)
    point = face.valueAt(u, v)
    if float(face.distToShape(Part.Vertex(point))[0]) > 0.01:
        raise RuntimeError("La ranura TCOM-%02d no pertenece a la cara superior." % circuit_number)
    return point


def _reserved_port_map(doc, boxes):
    box_names = {box.Name for box in boxes}
    reserved = {name: set() for name in box_names}
    for obj in doc.Objects:
        object_name = _safe(getattr(obj, "Name", ""))
        if not object_name.startswith(("EMT_Conexion", "Alimentador_", "Ramal_")):
            continue
        if _safe(getattr(obj, "GeneradoPor", "")) == GENERATED_BY:
            continue
        properties = set(getattr(obj, "PropertiesList", []) or [])
        if "CajaDestino" in properties:
            destination_name = _safe(getattr(obj, "CajaDestino", ""))
            name = _safe(getattr(obj, "PuertoDestino", ""))
            if destination_name in reserved and name:
                reserved[destination_name].add(name)
        if "CajaOrigen" in properties:
            source_box = getattr(obj, "CajaOrigen", None)
            name = _safe(getattr(obj, "PuertoOrigen", ""))
            if source_box is not None and getattr(source_box, "Name", "") in reserved and name:
                reserved[source_box.Name].add(name)
        if "CajaDestinoLink" in properties:
            destination_box = getattr(obj, "CajaDestinoLink", None)
            name = _safe(getattr(obj, "PuertoDestino", ""))
            if destination_box is not None and getattr(destination_box, "Name", "") in reserved and name:
                reserved[destination_box.Name].add(name)
    return reserved


def _source_port_available(box, panel_center, reserved):
    ports = [p for p in _H["_box_ports_world"](box) if p["name"].lower() != "bottom"]
    if not ports:
        return _H["_source_port_toward_panel"](box, panel_center)

    def score(port):
        direction = _H["_normalize_xy"](port["dir"])
        toward = _H["_normalize_xy"](panel_center - port["point"])
        return (1 if port["name"] in reserved else 0, -float(direction.dot(toward)), port["name"])

    chosen = sorted(ports, key=score)[0]
    if chosen["name"] in reserved:
        _warn("Todos los puertos laterales de '{}' estan ocupados; se reutilizara {}.".format(box.Label, chosen["name"]))
    return chosen["point"], _H["_normalize_xy"](chosen["dir"]), chosen["name"]


def _find_existing(doc, circuit_id):
    for obj in doc.Objects:
        if _safe(getattr(obj, "GeneradoPor", "")) == GENERATED_BY and _safe(getattr(obj, "CircuitoID", "")) == circuit_id:
            return obj
    return None


def _ensure_group(doc, circuit_group, circuit_id):
    label = "Alimentadores " + circuit_id
    for child in list(getattr(circuit_group, "Group", []) or []):
        if hasattr(child, "Group") and _safe(getattr(child, "Label", "")) == label:
            return child
    name = _H["_unique_name"](doc, "Grupo_Alimentadores_" + circuit_id.replace("-", "_"))
    group = doc.addObject("App::DocumentObjectGroup", name)
    group.Label = label
    _ensure_property(group, "App::PropertyString", "GeneradoPor", "ElectricCR", "Generador")
    group.GeneradoPor = GENERATED_BY
    circuit_group.addObject(group)
    return group


def _move_to_group(obj, target):
    for parent in list(getattr(obj, "InList", []) or []):
        if parent is target or not hasattr(parent, "Group"):
            continue
        if _safe(getattr(parent, "GeneradoPor", "")) == GENERATED_BY:
            try:
                parent.removeObject(obj)
            except Exception:
                pass
    target.addObject(obj)


def _style(obj):
    try:
        color = (0.78, 0.20, 0.95)
        obj.ViewObject.LineColor = color
        obj.ViewObject.PointColor = color
        obj.ViewObject.ShapeColor = color
        obj.ViewObject.LineWidth = 3.5
    except Exception:
        pass


def _write_feeder(doc, job, points, panel, face_index, cfg):
    circuit_id = job["circuit_id"]
    obj = _find_existing(doc, circuit_id)
    created = obj is None
    if obj is None:
        obj = doc.addObject("Part::Feature", _H["_unique_name"](doc, "Alimentador_" + circuit_id.replace("-", "_")))
    obj.Label = "Alimentador %s -> TCOM (Top)" % circuit_id
    obj.Shape = _H["_rounded_wire"](points, float(cfg["bend_radius"]))
    properties = [
        ("App::PropertyString", "GeneradoPor", "ElectricCR", "Generador"),
        ("App::PropertyString", "CircuitoID", "ElectricCR", "Circuito"),
        ("App::PropertyString", "CaraTablero", "Tablero", "Cara"),
        ("App::PropertyInteger", "FaceIndexTablero", "Tablero", "Indice"),
        ("App::PropertyInteger", "SlotTablero", "Tablero", "Ranura"),
        ("App::PropertyBool", "EsCaraRealTablero", "Tablero", "Cara real"),
        ("App::PropertyLink", "CajaOrigen", "Vinculos", "Caja origen"),
        ("App::PropertyLink", "TableroDestino", "Vinculos", "Tablero"),
        ("App::PropertyString", "PuertoOrigen", "Puertos", "Puerto"),
        ("App::PropertyVector", "PuntoOrigen", "Puertos", "Inicio"),
        ("App::PropertyVector", "PuntoDestino", "Puertos", "Destino"),
        ("App::PropertyFloat", "AlturaRuta", "Ruta", "Cota"),
        ("App::PropertyString", "RutaJSON", "Ruta", "Puntos"),
        ("App::PropertyString", "EstadoConexion", "Ruta", "Estado"),
    ]
    for data in properties:
        _ensure_property(obj, *data)
    obj.GeneradoPor = GENERATED_BY
    obj.CircuitoID = circuit_id
    obj.CaraTablero = "Top"
    obj.FaceIndexTablero = int(face_index)
    obj.SlotTablero = int(job["number"])
    obj.EsCaraRealTablero = True
    obj.CajaOrigen = job["source_box"]
    obj.TableroDestino = panel
    obj.PuertoOrigen = job["source_port_name"]
    obj.PuntoOrigen = App.Vector(job["source_point"])
    obj.PuntoDestino = App.Vector(job["destination"])
    obj.AlturaRuta = float(cfg["route_z"])
    obj.RutaJSON = json.dumps([[p.x, p.y, p.z] for p in points], separators=(",", ":"))
    obj.EstadoConexion = "Conectado"
    _style(obj)
    _move_to_group(obj, _ensure_group(doc, job["circuit_group"], circuit_id))
    return obj, created


def _default_cfg():
    p = App.ParamGet(PARAM_PATH)
    return {
        "route_z": float(p.GetFloat("route_z", DEFAULT_ROUTE_Z)),
        "lane_spacing": float(p.GetFloat("lane_spacing", DEFAULT_LANE_SPACING)),
        "approach_clearance": float(p.GetFloat("approach_clearance", DEFAULT_APPROACH_CLEARANCE)),
        "bend_radius": float(p.GetFloat("bend_radius", DEFAULT_BEND_RADIUS)),
        "port_stub": float(p.GetFloat("port_stub", DEFAULT_PORT_STUB)),
    }


def _save_cfg(cfg):
    p = App.ParamGet(PARAM_PATH)
    for key, value in cfg.items():
        p.SetFloat(key, float(value))


def _run_dialog(panel, face_index, circuit_map):
    cfg = _default_cfg()
    if (not GUI_UP) or QtWidgets is None:
        return cfg
    dlg = QtWidgets.QDialog(Gui.getMainWindow())
    dlg.setWindowTitle("Circuitos TCOM a cara superior")
    dlg.setMinimumWidth(520)
    info = QtWidgets.QLabel(
        "Tablero: {} | Face{} | circuitos: {}".format(
            panel.Label, face_index, ", ".join("TCOM-%02d" % n for n in sorted(circuit_map))
        )
    )
    form = QtWidgets.QFormLayout()
    controls = {}
    specs = [
        ("route_z", "Altura de rutas:", 3001.0, 10000.0),
        ("lane_spacing", "Separacion de carriles:", 10.0, 500.0),
        ("approach_clearance", "Separacion al tablero:", 50.0, 3000.0),
        ("bend_radius", "Radio de curvas:", 0.0, 1000.0),
        ("port_stub", "Salida desde caja:", 10.0, 500.0),
    ]
    for key, label, minimum, maximum in specs:
        spin = QtWidgets.QDoubleSpinBox(); spin.setRange(minimum, maximum); spin.setDecimals(1); spin.setSuffix(" mm"); spin.setValue(cfg[key])
        controls[key] = spin; form.addRow(label, spin)
    buttons = QtWidgets.QDialogButtonBox(QtWidgets.QDialogButtonBox.Ok | QtWidgets.QDialogButtonBox.Cancel)
    buttons.accepted.connect(dlg.accept); buttons.rejected.connect(dlg.reject)
    layout = QtWidgets.QVBoxLayout(dlg); layout.addWidget(info); layout.addLayout(form); layout.addWidget(buttons)
    execute = getattr(dlg, "exec", None) or getattr(dlg, "exec_", None)
    if execute() != QtWidgets.QDialog.Accepted:
        return None
    for key, control in controls.items(): cfg[key] = float(control.value())
    _save_cfg(cfg)
    return cfg


def main(doc_override=None, cfg_override=None):
    doc = doc_override or App.ActiveDocument
    if doc is None:
        _err("No hay documento activo."); return None
    try:
        panel = _find_tcom_panel(doc)
        face_index, face, center, _normal = _H["_top_face_from_panel"](panel)
    except Exception as exc:
        _err(exc); return None
    circuit_map = _find_circuit_groups(doc)
    if not circuit_map:
        _warn("No se encontraron circuitos TCOM con octogonales."); return None
    cfg = dict(cfg_override) if cfg_override is not None else _run_dialog(panel, face_index, circuit_map)
    if cfg is None:
        return None
    defaults = _default_cfg()
    for key in defaults: cfg[key] = float(cfg.get(key, defaults[key]))
    cfg["route_z"] = max(3001.0, cfg["route_z"])

    jobs = []
    all_boxes = list({box.Name: box for _group, boxes in circuit_map.values() for box in boxes}.values())
    reserved_map = _reserved_port_map(doc, all_boxes)
    for number in sorted(circuit_map):
        group, boxes = circuit_map[number]
        box = _H["_nearest_source_box"](boxes, center)
        source, direction, port_name = _source_port_available(box, center, reserved_map.get(box.Name, set()))
        destination = _slot_point_on_face(face, number)
        jobs.append({
            "number": number, "circuit_id": "TCOM-%02d" % number, "circuit_group": group,
            "source_box": box, "source_point": source, "source_direction": direction,
            "source_port_name": port_name, "destination": destination,
            "side": _H["_route_side"](source, panel.Shape.BoundBox),
        })
    sides = {}
    for job in jobs: sides.setdefault(job["side"], []).append(job)
    for values in sides.values(): values.sort(key=lambda job: job["number"])

    created = updated = 0
    doc.openTransaction("ElectricCR: conectar circuitos TCOM a cara superior")
    try:
        for _side, values in sides.items():
            for rank, job in enumerate(values):
                points = _H["_route_points"](job, rank, cfg, panel.Shape.BoundBox)
                _obj, was_created = _write_feeder(doc, job, points, panel, face_index, cfg)
                created += int(was_created); updated += int(not was_created)
        doc.recompute(); doc.commitTransaction()
    except Exception as exc:
        try: doc.abortTransaction()
        except Exception: pass
        _err("Fallo general: " + str(exc)); return None
    result = {"tablero": panel.Name, "cara": face_index, "cara_z": face.BoundBox.ZMax, "circuitos": len(jobs), "creados": created, "actualizados": updated}
    _log("Finalizado: " + json.dumps(result, ensure_ascii=False)); return result


if __name__ == "__main__":
    main()

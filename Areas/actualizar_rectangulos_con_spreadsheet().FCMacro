# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

import FreeCAD
import FreeCADGui

try:
    from PySide2 import QtWidgets
except Exception:
    try:
        from PySide import QtGui as QtWidgets
    except Exception:
        QtWidgets = None


def _warn_gui(title, message):
    if QtWidgets is None:
        return
    try:
        QtWidgets.QMessageBox.warning(None, title, message)
    except Exception:
        pass


def _sheet_candidates(doc):
    return [obj for obj in (getattr(doc, "Objects", []) or []) if getattr(obj, "TypeId", "") == "Spreadsheet::Sheet"]


def _is_group_container(obj):
    if obj is None:
        return False
    type_id = getattr(obj, "TypeId", "")
    if type_id == "App::DocumentObjectGroup":
        return True
    if type_id == "App::Part":
        return True
    return hasattr(obj, "Group")


def _find_parent_group_for_object(doc, target_obj):
    if target_obj is None:
        return None

    for parent in getattr(target_obj, "InList", []) or []:
        if _is_group_container(parent):
            return parent

    for obj in getattr(doc, "Objects", []) or []:
        if not _is_group_container(obj):
            continue
        try:
            if target_obj in (getattr(obj, "Group", []) or []):
                return obj
        except Exception:
            continue
    return None


def _pick_default_sheet(hojas_disponibles):
    if not hojas_disponibles:
        return None
    for hoja in hojas_disponibles:
        if getattr(hoja, "Name", "") == "DatosRecintos" or getattr(hoja, "Label", "") == "DatosRecintos":
            return hoja
    return hojas_disponibles[0]


def seleccionar_hoja_de_calculo():
    doc = FreeCAD.ActiveDocument
    hojas_disponibles = _sheet_candidates(doc)

    if not hojas_disponibles:
        FreeCAD.Console.PrintError("No hay hojas de calculo disponibles en el documento.\n")
        _warn_gui("Sin hojas", "No hay hojas de calculo disponibles en el documento.")
        return None

    if QtWidgets is None:
        hoja = _pick_default_sheet(hojas_disponibles)
        if hoja is not None:
            FreeCAD.Console.PrintWarning(
                "Qt no esta disponible; se usa la hoja '{}' automaticamente.\n".format(
                    getattr(hoja, "Label", getattr(hoja, "Name", ""))
                )
            )
        return hoja

    dialog = QtWidgets.QDialog()
    dialog.setWindowTitle("Seleccionar Hoja de Calculo")
    layout = QtWidgets.QVBoxLayout(dialog)

    combobox = QtWidgets.QComboBox()
    for hoja in hojas_disponibles:
        combobox.addItem(getattr(hoja, "Label", getattr(hoja, "Name", "")))
    layout.addWidget(combobox)

    botones = QtWidgets.QDialogButtonBox(QtWidgets.QDialogButtonBox.Ok | QtWidgets.QDialogButtonBox.Cancel)
    layout.addWidget(botones)

    botones.accepted.connect(dialog.accept)
    botones.rejected.connect(dialog.reject)

    exec_fn = getattr(dialog, "exec", None)
    if callable(exec_fn):
        accepted = dialog.exec() == QtWidgets.QDialog.Accepted
    else:
        accepted = dialog.exec_() == QtWidgets.QDialog.Accepted

    if not accepted:
        return None

    hoja_seleccionada_label = combobox.currentText()
    for hoja in hojas_disponibles:
        if getattr(hoja, "Label", "") == hoja_seleccionada_label:
            return hoja

    return _pick_default_sheet(hojas_disponibles)


def obtener_grupo_seleccionado():
    doc = FreeCAD.ActiveDocument
    selected_objects = FreeCADGui.Selection.getSelection()

    if not selected_objects:
        FreeCAD.Console.PrintError("No se ha seleccionado ningun objeto.\n")
        return None

    selected = selected_objects[0]
    if _is_group_container(selected):
        return selected

    parent_group = _find_parent_group_for_object(doc, selected)
    if parent_group is not None:
        FreeCAD.Console.PrintMessage(
            "Seleccion detectada dentro de un grupo. Se usa el grupo '{}'.\n".format(
                getattr(parent_group, "Label", getattr(parent_group, "Name", ""))
            )
        )
        return parent_group

    FreeCAD.Console.PrintError("El objeto seleccionado no es un grupo.\n")
    return None


def actualizar_rectangulos_con_spreadsheet():
    hoja = seleccionar_hoja_de_calculo()
    if not hoja:
        FreeCAD.Console.PrintError("No se selecciono una hoja de calculo valida.\n")
        return

    grupo = obtener_grupo_seleccionado()
    if not grupo:
        return

    FreeCAD.Console.PrintMessage("Grupo seleccionado: {}\n".format(getattr(grupo, "Label", getattr(grupo, "Name", ""))))
    FreeCAD.Console.PrintMessage("Hoja seleccionada: {}\n".format(getattr(hoja, "Label", getattr(hoja, "Name", ""))))

    data_luminarias = {}
    fila = 2

    while True:
        try:
            celda_actual = hoja.get("A{}".format(fila))
        except Exception as exc:
            FreeCAD.Console.PrintError("Error accediendo a la celda A{}: {}\n".format(fila, exc))
            break

        if not celda_actual:
            break

        data_luminarias[fila] = celda_actual
        fila += 1

    FreeCAD.Console.PrintMessage(
        "Filas leidas desde la hoja '{}': {}\n".format(
            getattr(hoja, "Label", getattr(hoja, "Name", "")),
            len(data_luminarias),
        )
    )

    # Placeholder legacy: la macro original se quedaba aqui para continuar la
    # actualizacion de rectangulos usando la informacion leida del spreadsheet.


actualizar_rectangulos_con_spreadsheet()

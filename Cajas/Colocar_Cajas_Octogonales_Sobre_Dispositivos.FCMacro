# -*- coding: utf-8 -*-
# MenuText: Colocar Cajas Octogonales sobre Dispositivos
# Icon: Cajas/Colocar_Cajas_Octogonales_Sobre_Dispositivos.svg

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

"""
Coloca una caja EMT octogonal sobre cada dispositivo tipo Tomacorriente/Apagador.

Reglas:
- Usa ElectricCR.electriccr.features.caja_emt_octogonal.insertar_caja_emt_octogonal_link
- Evita duplicados por llave de origen.
- Destino preferido:
    electrico/Tomacorrientes|Apagadores/<Circuito>/Cajas
- Fallback:
    electrico/Cajas/Cajas_Octogonales/...
- Si hay seleccion: procesa solo seleccion (objetos o grupos).
- Sin seleccion: procesa todo el documento.
"""

from pathlib import Path
import importlib
import importlib.util
import re
import sys
import unicodedata

import FreeCAD as App

try:
    import FreeCADGui as Gui
    GUI_UP = True
except Exception:
    Gui = None
    GUI_UP = False

try:
    from PySide2 import QtWidgets, QtCore
except Exception:
    try:
        from PySide import QtGui as QtWidgets  # type: ignore
        from PySide import QtCore  # type: ignore
    except Exception:
        QtWidgets = None
        QtCore = None


DEFAULT_DIAMETER = 22.2
DEFAULT_Z_OFFSET = 0.0
CEILING_SNPT_MM = 3000.0
NAME_PREFIX = "Caja EMT Octogonal"
PARAM_PATH = "User parameter:BaseApp/Preferences/Mod/ElectricCR/CajasOctogonales"


def _prefs():
    try:
        return App.ParamGet(PARAM_PATH)
    except Exception:
        return None


def _pref_get_bool(key, default):
    p = _prefs()
    if p is None:
        return bool(default)
    try:
        return bool(p.GetBool(str(key), bool(default)))
    except Exception:
        return bool(default)


def _pref_get_float(key, default):
    p = _prefs()
    if p is None:
        return float(default)
    try:
        return float(p.GetFloat(str(key), float(default)))
    except Exception:
        return float(default)


def _pref_get_str(key, default):
    p = _prefs()
    if p is None:
        return str(default)
    try:
        v = p.GetString(str(key), str(default))
        return str(v) if v is not None else str(default)
    except Exception:
        return str(default)


def _save_config(cfg):
    p = _prefs()
    if p is None:
        return
    try:
        p.SetString("scope", str(cfg.get("scope", "document")))
        p.SetBool("include_toma", bool(cfg.get("include_toma", True)))
        p.SetBool("include_apagador", bool(cfg.get("include_apagador", True)))
        p.SetBool("group_by_circuit", bool(cfg.get("group_by_circuit", True)))
        p.SetBool("prefer_group_circuit", bool(cfg.get("prefer_group_circuit", True)))
        p.SetBool("preserve_source_hierarchy", bool(cfg.get("preserve_source_hierarchy", True)))
        p.SetBool("place_in_source_circuit_group", bool(cfg.get("place_in_source_circuit_group", True)))
        p.SetBool("strict_devices_only", bool(cfg.get("strict_devices_only", True)))
        p.SetBool("skip_connection_like", bool(cfg.get("skip_connection_like", True)))
        p.SetBool("respect_policy", bool(cfg.get("respect_policy", True)))
        p.SetBool("skip_existing", bool(cfg.get("skip_existing", True)))
        p.SetFloat("diameter", float(cfg.get("diameter", DEFAULT_DIAMETER)))
        p.SetFloat("snpt", float(cfg.get("snpt", CEILING_SNPT_MM)))
        p.SetFloat("z_offset", float(cfg.get("z_offset", DEFAULT_Z_OFFSET)))
    except Exception:
        pass


def _default_config(has_selection):
    return {
        "scope": _pref_get_str("scope", "selection" if has_selection else "document"),
        "include_toma": _pref_get_bool("include_toma", True),
        "include_apagador": _pref_get_bool("include_apagador", True),
        "group_by_circuit": _pref_get_bool("group_by_circuit", True),
        "prefer_group_circuit": _pref_get_bool("prefer_group_circuit", True),
        "preserve_source_hierarchy": _pref_get_bool("preserve_source_hierarchy", True),
        "place_in_source_circuit_group": _pref_get_bool("place_in_source_circuit_group", True),
        "strict_devices_only": _pref_get_bool("strict_devices_only", True),
        "skip_connection_like": _pref_get_bool("skip_connection_like", True),
        "respect_policy": _pref_get_bool("respect_policy", True),
        "skip_existing": _pref_get_bool("skip_existing", True),
        "diameter": _pref_get_float("diameter", DEFAULT_DIAMETER),
        "snpt": _pref_get_float("snpt", CEILING_SNPT_MM),
        "z_offset": _pref_get_float("z_offset", DEFAULT_Z_OFFSET),
    }


class _ConfigDialog(object):
    """Dialogo de configuracion para corrida de cajas EMT."""

    def __init__(self, has_selection):
        self.has_selection = bool(has_selection)
        self.result = None

    def run(self):
        cfg = _default_config(self.has_selection)
        if not GUI_UP or QtWidgets is None:
            return cfg

        parent = None
        try:
            parent = Gui.getMainWindow()
        except Exception:
            parent = None

        dlg = QtWidgets.QDialog(parent)
        dlg.setWindowTitle("Configurar Cajas Octogonales")
        dlg.setMinimumWidth(520)
        dlg.setWindowModality(QtCore.Qt.WindowModal if QtCore else dlg.windowModality())

        hdr = QtWidgets.QLabel(
            "Colocar cajas EMT octogonales sobre dispositivos.\n"
            "Se recomienda mantener filtros estrictos para evitar conexiones 2D."
        )
        hdr.setWordWrap(True)
        hdr.setStyleSheet("color:#4b5563;")

        # Alcance
        grp_scope = QtWidgets.QGroupBox("Alcance")
        rb_doc = QtWidgets.QRadioButton("Todo el documento")
        rb_sel = QtWidgets.QRadioButton("Solo seleccion actual")
        rb_sel.setEnabled(self.has_selection)
        if self.has_selection and cfg.get("scope") == "selection":
            rb_sel.setChecked(True)
        else:
            rb_doc.setChecked(True)
        lay_scope = QtWidgets.QVBoxLayout(grp_scope)
        lay_scope.addWidget(rb_doc)
        lay_scope.addWidget(rb_sel)
        if not self.has_selection:
            tip = QtWidgets.QLabel("No hay seleccion activa. Se usara todo el documento.")
            tip.setWordWrap(True)
            tip.setStyleSheet("color: #888;")
            lay_scope.addWidget(tip)

        # Tipos
        grp_types = QtWidgets.QGroupBox("Dispositivos")
        chk_toma = QtWidgets.QCheckBox("Tomacorrientes")
        chk_toma.setChecked(bool(cfg.get("include_toma", True)))
        chk_apa = QtWidgets.QCheckBox("Apagadores")
        chk_apa.setChecked(bool(cfg.get("include_apagador", True)))
        lay_types = QtWidgets.QHBoxLayout(grp_types)
        lay_types.addWidget(chk_toma)
        lay_types.addWidget(chk_apa)
        lay_types.addStretch(1)

        # Reglas
        grp_rules = QtWidgets.QGroupBox("Reglas")
        chk_strict = QtWidgets.QCheckBox("Filtro estricto: solo objetos ElectricCR")
        chk_strict.setChecked(bool(cfg.get("strict_devices_only", True)))
        chk_conn = QtWidgets.QCheckBox("Excluir conexiones/planta 2D")
        chk_conn.setChecked(bool(cfg.get("skip_connection_like", True)))
        chk_policy = QtWidgets.QCheckBox("Respetar UsarCajaOctogonal / ConexionDirecta")
        chk_policy.setChecked(bool(cfg.get("respect_policy", True)))
        chk_existing = QtWidgets.QCheckBox("Omitir si ya existe caja para el origen")
        chk_existing.setChecked(bool(cfg.get("skip_existing", True)))
        chk_by_circuit = QtWidgets.QCheckBox("Ordenar por circuito (regla general)")
        chk_by_circuit.setChecked(bool(cfg.get("group_by_circuit", True)))
        chk_pref_group = QtWidgets.QCheckBox("Priorizar grupos de circuito existentes")
        chk_pref_group.setChecked(bool(cfg.get("prefer_group_circuit", True)))
        chk_place_src_circuit = QtWidgets.QCheckBox("Colocar en <Circuito>/Cajas del origen")
        chk_place_src_circuit.setChecked(bool(cfg.get("place_in_source_circuit_group", True)))
        chk_preserve = QtWidgets.QCheckBox("Mantener subgrupos origen (Tomacorrientes/Apagadores)")
        chk_preserve.setChecked(bool(cfg.get("preserve_source_hierarchy", True)))
        lay_rules = QtWidgets.QVBoxLayout(grp_rules)
        lay_rules.addWidget(chk_place_src_circuit)
        lay_rules.addWidget(chk_preserve)
        lay_rules.addWidget(chk_by_circuit)
        lay_rules.addWidget(chk_pref_group)
        lay_rules.addWidget(chk_strict)
        lay_rules.addWidget(chk_conn)
        lay_rules.addWidget(chk_policy)
        lay_rules.addWidget(chk_existing)

        # Geometria
        grp_geo = QtWidgets.QGroupBox("Geometria")
        sp_snpt = QtWidgets.QDoubleSpinBox()
        sp_snpt.setRange(-5000.0, 20000.0)
        sp_snpt.setDecimals(1)
        sp_snpt.setSuffix(" mm")
        sp_snpt.setValue(float(cfg.get("snpt", CEILING_SNPT_MM)))

        sp_offset = QtWidgets.QDoubleSpinBox()
        sp_offset.setRange(-5000.0, 5000.0)
        sp_offset.setDecimals(1)
        sp_offset.setSuffix(" mm")
        sp_offset.setValue(float(cfg.get("z_offset", DEFAULT_Z_OFFSET)))

        sp_diam = QtWidgets.QDoubleSpinBox()
        sp_diam.setRange(1.0, 200.0)
        sp_diam.setDecimals(1)
        sp_diam.setSuffix(" mm")
        sp_diam.setValue(float(cfg.get("diameter", DEFAULT_DIAMETER)))

        form_geo = QtWidgets.QFormLayout(grp_geo)
        form_geo.addRow("Nivel SNPT:", sp_snpt)
        form_geo.addRow("Offset Z adicional:", sp_offset)
        form_geo.addRow("Diametro EMT:", sp_diam)

        buttons = QtWidgets.QDialogButtonBox(QtWidgets.QDialogButtonBox.Ok | QtWidgets.QDialogButtonBox.Cancel)
        buttons.accepted.connect(dlg.accept)
        buttons.rejected.connect(dlg.reject)

        lay = QtWidgets.QVBoxLayout(dlg)
        lay.addWidget(hdr)
        lay.addWidget(grp_scope)
        lay.addWidget(grp_types)
        lay.addWidget(grp_rules)
        lay.addWidget(grp_geo)
        lay.addWidget(buttons)

        if dlg.exec_() != QtWidgets.QDialog.Accepted:
            return None

        cfg["scope"] = "selection" if (self.has_selection and rb_sel.isChecked()) else "document"
        cfg["include_toma"] = bool(chk_toma.isChecked())
        cfg["include_apagador"] = bool(chk_apa.isChecked())
        cfg["place_in_source_circuit_group"] = bool(chk_place_src_circuit.isChecked())
        cfg["preserve_source_hierarchy"] = bool(chk_preserve.isChecked())
        cfg["group_by_circuit"] = bool(chk_by_circuit.isChecked())
        cfg["prefer_group_circuit"] = bool(chk_pref_group.isChecked())
        cfg["strict_devices_only"] = bool(chk_strict.isChecked())
        cfg["skip_connection_like"] = bool(chk_conn.isChecked())
        cfg["respect_policy"] = bool(chk_policy.isChecked())
        cfg["skip_existing"] = bool(chk_existing.isChecked())
        cfg["snpt"] = float(sp_snpt.value())
        cfg["z_offset"] = float(sp_offset.value())
        cfg["diameter"] = float(sp_diam.value())
        _save_config(cfg)
        return cfg


def _log(msg):
    App.Console.PrintMessage(f"[CAJA_EMT_BULK][INFO] {msg}\n")


def _warn(msg):
    App.Console.PrintWarning(f"[CAJA_EMT_BULK][WARN] {msg}\n")


def _err(msg):
    App.Console.PrintError(f"[CAJA_EMT_BULK][ERROR] {msg}\n")


def _safe_text(value):
    try:
        return str(value or "")
    except Exception:
        return ""


def _safe_name_token(value, fallback="Caja_EMT"):
    txt = _safe_text(value).strip()
    if not txt:
        return fallback
    txt = re.sub(r"[^0-9A-Za-z_]+", "_", txt)
    txt = re.sub(r"_+", "_", txt).strip("_")
    return txt or fallback


def _norm_text(value):
    txt = _safe_text(value).strip().lower()
    if not txt:
        return ""
    try:
        txt = unicodedata.normalize("NFKD", txt)
        txt = "".join(ch for ch in txt if not unicodedata.combining(ch))
    except Exception:
        pass
    txt = re.sub(r"\s+", " ", txt).strip()
    return txt


def _as_float(value, default=0.0):
    try:
        if hasattr(value, "Value"):
            return float(value.Value)
        return float(value)
    except Exception:
        return float(default)


def _is_group(obj):
    try:
        if obj and obj.isDerivedFrom("App::DocumentObjectGroup"):
            return True
    except Exception:
        pass
    try:
        if obj and obj.isDerivedFrom("App::Part"):
            return True
    except Exception:
        pass
    return bool(obj and hasattr(obj, "Group"))


def _linked_object(obj):
    if obj is None:
        return None
    for attr in ("LinkedObject", "Link"):
        try:
            ref = getattr(obj, attr, None)
            if ref is not None:
                return ref
        except Exception:
            pass
    return None


def _as_group_obj(obj):
    if _is_group(obj):
        return obj
    ref = _linked_object(obj)
    if _is_group(ref):
        return ref
    return None


def _ensure_group(doc, name, parent=None, label=None):
    grp = doc.getObject(name)
    if grp is None:
        grp = doc.addObject("App::DocumentObjectGroup", name)
    if label:
        try:
            grp.Label = label
        except Exception:
            pass
    if parent is not None:
        try:
            if grp not in (parent.Group or []):
                parent.addObject(grp)
        except Exception:
            pass
    return grp


def _add_to_group(group, obj):
    if group is None or obj is None:
        return
    try:
        if obj not in (group.Group or []):
            group.addObject(obj)
    except Exception:
        pass


def _remove_from_group(group, obj):
    if group is None or obj is None:
        return
    try:
        if obj in (group.Group or []):
            group.removeObject(obj)
    except Exception:
        pass


def _ensure_target_groups(doc):
    g_elec = _ensure_group(doc, "electrico", parent=None, label="electrico")
    g_cajas = _ensure_group(doc, "Cajas", parent=g_elec, label="Cajas")
    g_oct = _ensure_group(doc, "Cajas_Octogonales", parent=g_cajas, label="Cajas_Octogonales")
    g_toma = _ensure_group(doc, "Cajas_Octogonales_Tomacorrientes", parent=g_oct, label="Tomacorrientes")
    g_apa = _ensure_group(doc, "Cajas_Octogonales_Apagadores", parent=g_oct, label="Apagadores")
    g_circuitos = _ensure_group(doc, "Cajas_Octogonales_Circuitos", parent=g_oct, label="Circuitos")
    return g_cajas, g_oct, g_toma, g_apa, g_circuitos


def _sanitize_group_token(text, fallback="Sin_Circuito"):
    token = _safe_name_token(text, fallback=fallback)
    return token or fallback


def _source_circuit_from_ancestors(obj):
    try:
        for anc in _object_ancestors(obj):
            t = _safe_text(getattr(anc, "Label", "")) or _safe_text(getattr(anc, "Name", ""))
            if t and "circuit" in t.lower():
                return t.strip()
    except Exception:
        pass
    return ""


def _source_circuit_id(obj, prefer_group=True):
    if prefer_group:
        grp = _source_circuit_from_ancestors(obj)
        if grp:
            return grp

    for attr in ("CircuitoID", "Circuito_Grupo", "Circuito", "CircuitID"):
        try:
            value = _safe_text(getattr(obj, attr, "")).strip()
            if value:
                return value
        except Exception:
            pass

    if not prefer_group:
        grp = _source_circuit_from_ancestors(obj)
        if grp:
            return grp
    return "Sin_Circuito"


def _ensure_circuit_type_group(doc, g_circuitos, circuit_id, source_type):
    ctoken = _sanitize_group_token(circuit_id, fallback="Sin_Circuito")
    g_c = _ensure_group(
        doc,
        f"Cajas_Circuito_{ctoken}",
        parent=g_circuitos,
        label=_safe_text(circuit_id) or "Sin_Circuito",
    )
    suffix = "Tomacorrientes" if source_type == "Toma" else "Apagadores"
    g_t = _ensure_group(
        doc,
        f"Cajas_{ctoken}_{suffix}",
        parent=g_c,
        label=suffix,
    )
    return g_t


def _parent_group(obj):
    if obj is None:
        return None
    if hasattr(obj, "getParentGroup"):
        try:
            pg = obj.getParentGroup()
            if pg is not None:
                return pg
        except Exception:
            pass
    for parent in (getattr(obj, "InList", []) or []):
        if _is_group(parent):
            return parent
    return None


def _group_chain_topdown(obj):
    chain = []
    seen = set()
    cur = obj
    while True:
        pg = _parent_group(cur)
        if pg is None:
            break
        name = _safe_text(getattr(pg, "Name", ""))
        if not name or name in seen:
            break
        seen.add(name)
        chain.append(pg)
        cur = pg
    chain.reverse()
    return chain


def _child_index(parent, child):
    if parent is None or child is None:
        return 99999
    try:
        items = list(getattr(parent, "Group", []) or [])
        for i, it in enumerate(items):
            if it is child:
                return i
    except Exception:
        pass
    return 99999


def _matches_root_group(group_obj, source_type):
    txt = f"{_safe_text(getattr(group_obj, 'Name', ''))} {_safe_text(getattr(group_obj, 'Label', ''))}".lower()
    if source_type == "Toma":
        return ("tomacorr" in txt) or ("toma" in txt)
    if source_type == "Apagador":
        return ("apagador" in txt) or ("switch" in txt) or ("interruptor" in txt)
    return False


def _is_connection_group_label(group_obj):
    txt = f"{_safe_text(getattr(group_obj, 'Name', ''))} {_safe_text(getattr(group_obj, 'Label', ''))}".lower()
    return ("conexion" in txt) or ("conexiones" in txt)


def _is_circuit_group_label(group_obj):
    txt = f"{_safe_text(getattr(group_obj, 'Name', ''))} {_safe_text(getattr(group_obj, 'Label', ''))}".lower()
    if ("circuito" in txt) or ("circuit" in txt):
        return True
    return bool(re.search(r"\btp[\s\-_]*\d+", txt))


def _is_iluminacion_group_label(group_obj):
    txt = _norm_text(
        f"{_safe_text(getattr(group_obj, 'Name', ''))} {_safe_text(getattr(group_obj, 'Label', ''))}"
    )
    return "iluminacion" in txt


def _is_bucket_group_label(group_obj):
    txt = _norm_text(
        f"{_safe_text(getattr(group_obj, 'Name', ''))} {_safe_text(getattr(group_obj, 'Label', ''))}"
    )
    if not txt:
        return False
    if "conexion" in txt or "conexiones" in txt:
        return True
    if "componente" in txt or "componentes" in txt:
        return True
    if re.search(r"\bcircuitos\b", txt):
        return True
    if re.search(r"\brecintos\b", txt):
        return True
    return False


def _source_iluminacion_recinto_group(source_obj):
    chain = _group_chain_topdown(source_obj)
    if not chain:
        return None

    ilum_idx = None
    for i, g in enumerate(chain):
        if _is_iluminacion_group_label(g):
            ilum_idx = i
            break
    if ilum_idx is None:
        return None

    tail = chain[ilum_idx + 1:]
    if not tail:
        return None

    circuito = None
    recinto = None
    for g in tail:
        if _is_connection_group_label(g):
            continue
        if _is_bucket_group_label(g):
            continue
        if circuito is None:
            circuito = g
            continue
        recinto = g
        break

    return recinto or circuito


def _source_circuit_container_group(obj, source_type):
    chain = _group_chain_topdown(obj)
    root_idx = None
    for i, g in enumerate(chain):
        if _matches_root_group(g, source_type):
            root_idx = i
            break
    if root_idx is None:
        return None

    # Primero intentar localizar grupo de circuito explicito.
    for g in chain[root_idx + 1:]:
        if _is_connection_group_label(g):
            continue
        if _is_circuit_group_label(g):
            return g

    # Fallback: primer subgrupo funcional despues de Tomacorrientes/Apagadores.
    for g in chain[root_idx + 1:]:
        if not _is_connection_group_label(g):
            return g
    return None


def _source_group_context(obj, source_type):
    chain = _group_chain_topdown(obj)
    root_idx = None
    for i, g in enumerate(chain):
        if _matches_root_group(g, source_type):
            root_idx = i
            break
    if root_idx is None:
        return {"subgroups": [], "order_key": tuple()}

    # Subgrupos despues de Tomacorrientes/Apagadores; ignorar Conexiones*.
    subgroups = []
    for g in chain[root_idx + 1:]:
        if _is_connection_group_label(g):
            continue
        label = _safe_text(getattr(g, "Label", "")) or _safe_text(getattr(g, "Name", ""))
        if label:
            subgroups.append(label)

    # Clave de orden segun el orden actual en el arbol origen.
    idxs = []
    parent = chain[root_idx]
    for g in chain[root_idx + 1:]:
        idxs.append(_child_index(parent, g))
        parent = g
    idxs.append(_child_index(parent, obj))
    return {"subgroups": subgroups, "order_key": tuple(idxs)}


def _group_key(text):
    n = _norm_text(text)
    n = re.sub(r"[^0-9a-z]+", "", n)
    return n


def _split_suffix_digits(key):
    m = re.match(r"^(.*?)(\d+)$", _safe_text(key))
    if m:
        return m.group(1), m.group(2)
    return _safe_text(key), ""


def _keys_compatible(target_key, own_key):
    if (not target_key) or (not own_key):
        return False
    if target_key == own_key:
        return True
    t_base, t_suf = _split_suffix_digits(target_key)
    o_base, o_suf = _split_suffix_digits(own_key)
    if t_base and (t_base == o_base):
        # Permitir variantes con sufijo numerico solo si una de las dos no trae numero.
        # Ej: "Cajas_Octogonales" <-> "Cajas_Octogonales031"
        if (not t_suf and o_suf) or (t_suf and not o_suf):
            return True
    return False


def _find_child_group_by_label(parent, label):
    want = _safe_text(label).strip().lower()
    if not want:
        return None
    want_key = _group_key(want)
    for child in (getattr(parent, "Group", []) or []):
        grp = _as_group_obj(child)
        if grp is None:
            continue
        lbl = _safe_text(getattr(grp, "Label", "")).strip().lower()
        name = _safe_text(getattr(grp, "Name", "")).strip().lower()
        if lbl == want or name == want:
            return grp
        if _keys_compatible(want_key, _group_key(lbl)) or _keys_compatible(want_key, _group_key(name)):
            return grp
    return None


def _ensure_child_group_by_label(doc, parent, label, prefix="CajaOct"):
    token = _sanitize_group_token(label, fallback="Grupo")
    base = f"{prefix}_{_safe_name_token(getattr(parent, 'Name', 'Root'), 'Root')}_{token}"

    # Reusar grupo por nombre base si ya existe en el documento.
    grp_base = doc.getObject(base)
    if _is_group(grp_base):
        _add_to_group(parent, grp_base)
        return grp_base

    # Reusar algun sufijo existente si ya habia sido creado antes.
    reused = None
    for obj in (doc.Objects or []):
        try:
            n = _safe_text(getattr(obj, "Name", ""))
        except Exception:
            n = ""
        if not n:
            continue
        if n == base or n.startswith(base + "_"):
            grp = _as_group_obj(obj)
            if grp is None:
                continue
            reused = grp
            if n == base:
                break

    if reused is not None:
        _add_to_group(parent, reused)
        return reused

    existing = _find_child_group_by_label(parent, label)
    if existing is not None:
        return existing

    name = base
    i = 1
    while doc.getObject(name) is not None:
        name = f"{base}_{i:02d}"
        i += 1
    grp = doc.addObject("App::DocumentObjectGroup", name)
    try:
        grp.Label = _safe_text(label) or token
    except Exception:
        pass
    _add_to_group(parent, grp)
    return grp


def _ensure_hierarchy_target_group(doc, base_group, labels):
    cur = base_group
    for label in (labels or []):
        cur = _ensure_child_group_by_label(doc, cur, label)
    return cur


def _ensure_source_circuit_boxes_group(doc, source_obj, source_type):
    # Prioridad 0: si el origen vive en Iluminacion/Circuito/Recinto, colocar ahi.
    g_recinto_ilum = _source_iluminacion_recinto_group(source_obj)
    if g_recinto_ilum is not None and _is_group(g_recinto_ilum):
        return _ensure_child_group_by_label(doc, g_recinto_ilum, "Cajas_Octogonales", prefix="CajaOct")

    # Prioridad 1 (legacy): Tomacorrientes|Apagadores/<Circuito>/Cajas...
    circuit_group = _source_circuit_container_group(source_obj, source_type)
    if circuit_group is None or not _is_group(circuit_group):
        return None

    circuit_label = _safe_text(getattr(circuit_group, "Label", "")) or _safe_text(getattr(circuit_group, "Name", ""))
    circuit_label = circuit_label.strip() or "Sin_Circuito"
    boxes_label = f"Cajas_{circuit_label}"

    # Compatibilidad: si ya existe el grupo legado "Cajas", reutilizarlo y actualizar etiqueta.
    legacy = _find_child_group_by_label(circuit_group, "Cajas")
    if legacy is not None:
        try:
            legacy.Label = boxes_label
        except Exception:
            pass
        return legacy

    return _ensure_child_group_by_label(doc, circuit_group, boxes_label, prefix="CajaOct")


def _object_ancestors(obj):
    seen = set()
    cur_list = list(getattr(obj, "InList", []) or [])
    out = []
    while cur_list:
        nxt = cur_list.pop(0)
        if nxt is None:
            continue
        name = _safe_text(getattr(nxt, "Name", ""))
        if not name or name in seen:
            continue
        seen.add(name)
        out.append(nxt)
        for parent in (getattr(nxt, "InList", []) or []):
            if parent is not None:
                cur_list.append(parent)
    return out


def _is_library_object(obj):
    name = _safe_text(getattr(obj, "Name", "")).lower()
    label = _safe_text(getattr(obj, "Label", "")).lower()
    if name.startswith("master_") or name.startswith("proto"):
        return True
    if label.startswith("master ") or label.startswith("proto"):
        return True
    for anc in _object_ancestors(obj):
        an = _safe_text(getattr(anc, "Name", "")).lower()
        al = _safe_text(getattr(anc, "Label", "")).lower()
        if an.startswith("_lib") or al.startswith("_lib"):
            return True
    return False


def _ensure_electriccr_on_path():
    for mod_name in ("ElectricCR", "electriccr"):
        try:
            importlib.import_module(mod_name)
            return True
        except ImportError:
            pass

    try:
        here = Path(__file__).resolve()
    except Exception:
        here = None

    cands = []
    if here is not None:
        for parent in [here.parent, *here.parents]:
            pkg = parent / "ElectricCR"
            if pkg.is_dir():
                cands.extend([str(pkg.parent), str(pkg)])

    try:
        base = Path(App.getUserAppDataDir())
    except Exception:
        base = Path.home() / "AppData" / "Roaming" / "FreeCAD"

    for folder_name in ("Macro", "Macros"):
        pkg = base / folder_name / "ElectricCR"
        if pkg.is_dir():
            cands.extend([str(pkg.parent), str(pkg)])

    for p in cands:
        if p and p not in sys.path:
            sys.path.insert(0, p)

    importlib.invalidate_caches()
    for mod_name in ("ElectricCR", "electriccr"):
        try:
            importlib.import_module(mod_name)
            return True
        except ImportError:
            pass
    return False


def _import_caja_feature():
    if not _ensure_electriccr_on_path():
        raise RuntimeError("No se pudo resolver el paquete ElectricCR.")

    candidates = (
        "ElectricCR.electriccr.features.caja_emt_octogonal",
        "electriccr.features.caja_emt_octogonal",
    )
    for mod_name in candidates:
        try:
            mod = importlib.import_module(mod_name)
            insert_fn = getattr(mod, "insertar_caja_emt_octogonal_link", None)
            master_fn = getattr(mod, "crear_caja_emt_octogonal_master", None)
            if callable(insert_fn) and callable(master_fn):
                return mod, insert_fn, master_fn
        except Exception:
            pass
    raise RuntimeError("No se pudo importar caja_emt_octogonal.")


def _import_component_classifier():
    # 1) import directo si ya esta en sys.path
    try:
        mod = importlib.import_module("component_classifier")
        fn = getattr(mod, "get_component_type", None)
        if callable(fn):
            return fn
    except Exception:
        pass

    # 2) resolver por ruta relativa Conectar/component_classifier.py
    try:
        here = Path(__file__).resolve()
    except Exception:
        here = None
    if here is not None:
        for parent in [here.parent, *here.parents]:
            cand = parent / "Conectar" / "component_classifier.py"
            if cand.exists():
                try:
                    spec = importlib.util.spec_from_file_location("component_classifier_dynamic", str(cand))
                    if spec and spec.loader:
                        mod = importlib.util.module_from_spec(spec)
                        spec.loader.exec_module(mod)
                        fn = getattr(mod, "get_component_type", None)
                        if callable(fn):
                            return fn
                except Exception:
                    pass
    return None


def _fallback_component_type(obj):
    for attr in ("Tipo", "TipoLogico", "Categoria", "KeyRegistro"):
        try:
            txt = _safe_text(getattr(obj, attr, "")).lower()
        except Exception:
            txt = ""
        if not txt:
            continue
        if "apagador" in txt or "switch" in txt or "interruptor" in txt:
            return "Apagador"
        if "toma" in txt or "tomacorriente" in txt or "enchufe" in txt:
            return "Toma"

    name = f"{_safe_text(getattr(obj, 'Name', ''))} {_safe_text(getattr(obj, 'Label', ''))}".lower()
    if "apagador" in name or "switch" in name or "interruptor" in name:
        return "Apagador"
    if "toma" in name or "tomacorriente" in name or "enchufe" in name:
        return "Toma"
    return None


def _iter_selected_or_document_objects(doc, scope="document", selection_roots=None):
    sel = list(selection_roots or [])
    use_selection = (scope == "selection" and bool(sel))

    if not use_selection:
        for obj in (doc.Objects or []):
            yield obj
        return

    seen = set()

    def walk(obj):
        if obj is None:
            return
        name = _safe_text(getattr(obj, "Name", ""))
        if not name or name in seen:
            return
        seen.add(name)
        if _is_group(obj):
            for child in (getattr(obj, "Group", []) or []):
                for nested in walk(child):
                    yield nested
            return
        yield obj

    for root in sel:
        for obj in walk(root):
            yield obj


def _selection_roots():
    if not GUI_UP:
        return []
    try:
        return list(Gui.Selection.getSelection() or [])
    except Exception:
        return []


def _ensure_source_policy_properties(obj):
    """Asegura propiedades para controlar si el origen debe tener caja."""
    defs = [
        ("App::PropertyBool", "UsarCajaOctogonal", "Cajas", "Si false, no colocar caja octogonal"),
        ("App::PropertyBool", "ConexionDirecta", "Cajas", "Si true, se asume conexion directa sin caja"),
    ]
    created = set()
    for ptype, pname, pgroup, pdesc in defs:
        try:
            if pname not in obj.PropertiesList:
                obj.addProperty(ptype, pname, pgroup, pdesc)
                created.add(pname)
        except Exception:
            pass
    if "UsarCajaOctogonal" in created:
        try:
            obj.UsarCajaOctogonal = True
        except Exception:
            pass
    if "ConexionDirecta" in created:
        try:
            obj.ConexionDirecta = False
        except Exception:
            pass


def _source_allows_box(obj):
    _ensure_source_policy_properties(obj)
    try:
        if hasattr(obj, "ConexionDirecta") and bool(obj.ConexionDirecta):
            return False, "conexion_directa"
    except Exception:
        pass
    try:
        if hasattr(obj, "UsarCajaOctogonal") and not bool(obj.UsarCajaOctogonal):
            return False, "desactivado"
    except Exception:
        pass
    return True, ""


def _has_electriccr_device_signature(obj):
    keys = ("Tipo", "KeyRegistro", "AlturaRel", "ModoVisual", "OrientacionPared")
    try:
        if any(hasattr(obj, k) for k in keys):
            return True
    except Exception:
        pass
    try:
        linked = getattr(obj, "LinkedObject", None)
        if linked is not None and any(hasattr(linked, k) for k in keys):
            return True
    except Exception:
        pass
    return False


def _is_connection_like_object(obj):
    text = f"{_safe_text(getattr(obj, 'Name', ''))} {_safe_text(getattr(obj, 'Label', ''))}".lower()
    if "conexion" in text or "conexiones" in text:
        return True

    try:
        for anc in _object_ancestors(obj):
            t = f"{_safe_text(getattr(anc, 'Name', ''))} {_safe_text(getattr(anc, 'Label', ''))}".lower()
            if "conexion" in t or "conexiones" in t:
                return True
    except Exception:
        pass

    type_id = _safe_text(getattr(obj, "TypeId", "")).lower()
    if type_id and "app::link" not in type_id and "featurepython" not in type_id:
        tokens = ("wire", "line", "sketch", "draft", "bspline", "bezier", "circle", "arc")
        if any(tok in type_id for tok in tokens):
            return True

    proxy_type = _safe_text(getattr(getattr(obj, "Proxy", None), "Type", "")).lower()
    if proxy_type in {"wire", "line", "bspline", "bezier", "circle", "arc", "rectangle", "polygon"}:
        return True

    return False


def _source_anchor_world(obj):
    def _center_from_bb(bb):
        return App.Vector(
            0.5 * (bb.XMin + bb.XMax),
            0.5 * (bb.YMin + bb.YMax),
            0.5 * (bb.ZMin + bb.ZMax),
        )

    def _center_from_shapes(shapes):
        xmin = ymin = zmin = float("inf")
        xmax = ymax = zmax = float("-inf")
        used = False
        for sh in shapes:
            try:
                bb = sh.BoundBox
            except Exception:
                continue
            xmin = min(xmin, bb.XMin)
            ymin = min(ymin, bb.YMin)
            zmin = min(zmin, bb.ZMin)
            xmax = max(xmax, bb.XMax)
            ymax = max(ymax, bb.YMax)
            zmax = max(zmax, bb.ZMax)
            used = True
        if not used:
            return None
        return App.Vector(
            0.5 * (xmin + xmax),
            0.5 * (ymin + ymax),
            0.5 * (zmin + zmax),
        )

    try:
        shape = getattr(obj, "Shape", None)
        if shape is not None and not shape.isNull():
            # 1) Prioridad: geometria 3D (solidos), evita sesgo por simbolo 2D.
            solids = list(getattr(shape, "Solids", []) or [])
            if solids:
                c_sol = _center_from_shapes(solids)
                if c_sol:
                    return c_sol

            # 2) Fallback: caras con espesor Z (normalmente parte 3D).
            faces3d = []
            for fc in (getattr(shape, "Faces", []) or []):
                try:
                    fbb = fc.BoundBox
                    if fbb.ZLength > 1e-3:
                        faces3d.append(fc)
                except Exception:
                    pass
            if faces3d:
                c_f = _center_from_shapes(faces3d)
                if c_f:
                    return c_f

            # 3) Ultimo recurso: shape completa.
            return _center_from_bb(shape.BoundBox)
    except Exception:
        pass

    # Fallback por propiedades del objeto (insercion tipo objeto_toma_uno).
    try:
        base = obj.Placement.Base
    except Exception:
        base = App.Vector(0.0, 0.0, 0.0)

    offx = _as_float(getattr(obj, "OffsetX", 0.0), 0.0)
    offy = _as_float(getattr(obj, "OffsetY", 0.0), 0.0)
    altura = _as_float(getattr(obj, "AlturaRel", 0.0), 0.0)
    local = App.Vector(offx, offy, altura)
    return base + _source_rotation(obj).multVec(local)


def _source_rotation(obj):
    try:
        rot = obj.Placement.Rotation
    except Exception:
        rot = App.Rotation()

    giro = _as_float(getattr(obj, "Giro", 0.0), 0.0)
    if abs(giro) > 1e-9:
        extra = App.Rotation(App.Vector(0.0, 0.0, 1.0), giro)
        try:
            rot = rot.multiply(extra)
        except Exception:
            try:
                rot = rot * extra
            except Exception:
                pass
    return rot


def _source_key(obj):
    for attr in ("UUID",):
        try:
            txt = _safe_text(getattr(obj, attr, "")).strip()
            if txt:
                return f"UUID:{txt}"
        except Exception:
            pass
    return f"NAME:{_safe_text(getattr(obj, 'Name', ''))}"


def _target_key_set(groups):
    def iter_group_objs_recursive(group, seen):
        if group is None:
            return
        gname = _safe_text(getattr(group, "Name", ""))
        if gname and gname in seen:
            return
        if gname:
            seen.add(gname)
        for child in (getattr(group, "Group", []) or []):
            if _is_group(child):
                for x in iter_group_objs_recursive(child, seen):
                    yield x
            else:
                yield child

    keys = set()
    seen_groups = set()
    for grp in groups:
        for obj in iter_group_objs_recursive(grp, seen_groups):
            try:
                k = _safe_text(getattr(obj, "CajaOrigenKey", "")).strip()
                if k:
                    keys.add(k)
            except Exception:
                pass
    return keys


def _ensure_box_metadata(box_obj, source_obj, source_type, snpt_level, circuit_id):
    defs = [
        ("App::PropertyString", "CajaOrigenKey", "Vinculo", "Llave unica de objeto origen"),
        ("App::PropertyString", "CajaOrigenName", "Vinculo", "Name de objeto origen"),
        ("App::PropertyString", "CajaOrigenLabel", "Vinculo", "Label de objeto origen"),
        ("App::PropertyString", "CajaOrigenTipo", "Vinculo", "Tipo de objeto origen"),
        ("App::PropertyFloat", "AlturaOrigen", "Vinculo", "AlturaRel del origen (mm)"),
        ("App::PropertyString", "OrientacionOrigen", "Vinculo", "OrientacionPared del origen"),
        ("App::PropertyFloat", "GiroOrigen", "Vinculo", "Giro del origen (deg)"),
        ("App::PropertyString", "CircuitoID", "Circuito", "Identificador de circuito"),
        ("App::PropertyString", "Circuito_Grupo", "Circuito", "Grupo de circuito"),
        ("App::PropertyBool", "NodoDerivacion", "Red", "Marca como nodo de derivacion"),
        ("App::PropertyString", "EstadoConexion", "Red", "Estado de conexion de tuberia"),
        ("App::PropertyFloat", "NivelSNPT", "Red", "Cota SNPT objetivo (mm)"),
    ]
    for ptype, pname, pgroup, pdesc in defs:
        try:
            if pname not in box_obj.PropertiesList:
                box_obj.addProperty(ptype, pname, pgroup, pdesc)
        except Exception:
            pass

    try:
        box_obj.CajaOrigenKey = _source_key(source_obj)
    except Exception:
        pass
    try:
        box_obj.CajaOrigenName = _safe_text(getattr(source_obj, "Name", ""))
    except Exception:
        pass
    try:
        box_obj.CajaOrigenLabel = _safe_text(getattr(source_obj, "Label", ""))
    except Exception:
        pass
    try:
        box_obj.CajaOrigenTipo = _safe_text(source_type)
    except Exception:
        pass
    try:
        box_obj.AlturaOrigen = _as_float(getattr(source_obj, "AlturaRel", 0.0), 0.0)
    except Exception:
        pass
    try:
        box_obj.OrientacionOrigen = _safe_text(getattr(source_obj, "OrientacionPared", ""))
    except Exception:
        pass
    try:
        box_obj.GiroOrigen = _as_float(getattr(source_obj, "Giro", 0.0), 0.0)
    except Exception:
        pass
    try:
        box_obj.CircuitoID = _safe_text(circuit_id)
    except Exception:
        pass
    try:
        box_obj.Circuito_Grupo = _safe_text(circuit_id)
    except Exception:
        pass
    try:
        box_obj.NodoDerivacion = True
    except Exception:
        pass
    try:
        if not _safe_text(getattr(box_obj, "EstadoConexion", "")):
            box_obj.EstadoConexion = "Pendiente"
    except Exception:
        pass
    try:
        box_obj.NivelSNPT = float(snpt_level)
    except Exception:
        pass


def _natural_circuit_key(text):
    s = _safe_text(text).strip().lower()
    parts = re.split(r"(\d+)", s)
    out = []
    for p in parts:
        if p.isdigit():
            out.append(int(p))
        else:
            out.append(p)
    return tuple(out)


def _sort_candidates(items, group_by_circuit=True, preserve_hierarchy=False):
    # Orden estable: jerarquia origen (opcional), circuito (opcional), tipo, Y desc, X asc, label.
    def key_fn(item):
        obj = item["obj"]
        typ = item["type"]
        p = item["point"]
        circuit = item.get("circuit", "Sin_Circuito")
        circuit_key = _natural_circuit_key(circuit) if group_by_circuit else tuple()
        tree_key = item.get("tree_order", tuple()) if preserve_hierarchy else tuple()
        return (
            tree_key,
            circuit_key,
            0 if typ == "Toma" else 1,
            -float(getattr(p, "y", 0.0)),
            float(getattr(p, "x", 0.0)),
            _safe_text(getattr(obj, "Label", "")).lower(),
        )

    return sorted(items, key=key_fn)


def _build_box_placement(source_obj, anchor_local, z_offset, snpt_level):
    point = _source_anchor_world(source_obj)
    point = App.Vector(point.x, point.y, float(snpt_level))
    rot = _source_rotation(source_obj)
    local_shift = App.Vector(0.0, 0.0, float(z_offset))
    base = point + rot.multVec(local_shift) - rot.multVec(anchor_local)
    return App.Placement(base, rot)


def main():
    doc = App.ActiveDocument
    if doc is None:
        _err("No hay documento activo.")
        return

    selection_roots = _selection_roots()
    cfg = _ConfigDialog(bool(selection_roots)).run()
    if cfg is None:
        _warn("Operacion cancelada por el usuario.")
        return

    allowed_types = set()
    if cfg.get("include_toma", True):
        allowed_types.add("Toma")
    if cfg.get("include_apagador", True):
        allowed_types.add("Apagador")
    if not allowed_types:
        _warn("No se selecciono ningun tipo de dispositivo para procesar.")
        return

    try:
        _mod_box, insert_box_link, create_box_master = _import_caja_feature()
    except Exception as ex:
        _err(f"No se pudo cargar feature de caja EMT: {ex}")
        return

    get_component_type = _import_component_classifier()
    if get_component_type is None:
        _warn("No se pudo importar component_classifier; se usa deteccion basica.")

    g_cajas, _g_oct, g_toma, g_apa, g_circuitos = _ensure_target_groups(doc)

    try:
        master = create_box_master(doc=doc, hide_master=True)
        m_bb = master.Shape.BoundBox
        anchor_local = App.Vector(
            0.5 * (m_bb.XMin + m_bb.XMax),
            0.5 * (m_bb.YMin + m_bb.YMax),
            0.5 * (m_bb.ZMin + m_bb.ZMax),
        )
    except Exception as ex:
        _err(f"No se pudo preparar master de caja EMT: {ex}")
        return

    g_electrico = doc.getObject("electrico")
    g_tomas_src = doc.getObject("Tomacorrientes")
    g_apag_src = doc.getObject("Apagadores")
    existing_keys_all = _target_key_set([g_toma, g_apa, g_circuitos, g_tomas_src, g_apag_src, g_electrico])
    existing_keys = set(existing_keys_all) if cfg.get("skip_existing", True) else set()
    selection_mode = (cfg.get("scope") == "selection" and bool(selection_roots))

    candidates = []
    stats = {
        "scanned": 0,
        "group": 0,
        "library": 0,
        "not_type": 0,
        "strict": 0,
        "conn2d": 0,
        "existing": 0,
        "policy": 0,
    }

    for obj in _iter_selected_or_document_objects(
        doc,
        scope=cfg.get("scope", "document"),
        selection_roots=selection_roots,
    ):
        stats["scanned"] += 1
        if obj is None:
            continue
        if _is_group(obj):
            stats["group"] += 1
            continue
        if _is_library_object(obj):
            stats["library"] += 1
            continue
        if cfg.get("skip_connection_like", True) and _is_connection_like_object(obj):
            stats["conn2d"] += 1
            continue
        if cfg.get("strict_devices_only", True) and not _has_electriccr_device_signature(obj):
            stats["strict"] += 1
            continue

        ctype = None
        if callable(get_component_type):
            try:
                ctype = get_component_type(obj)
            except Exception:
                ctype = None
        if not ctype:
            ctype = _fallback_component_type(obj)
        if ctype not in allowed_types:
            stats["not_type"] += 1
            continue

        if cfg.get("respect_policy", True):
            allowed, _reason = _source_allows_box(obj)
            if not allowed:
                stats["policy"] += 1
                continue

        key = _source_key(obj)
        if key in existing_keys:
            stats["existing"] += 1
            continue

        hierarchy_ctx = _source_group_context(obj, ctype)
        candidates.append(
            {
                "obj": obj,
                "type": ctype,
                "key": key,
                "point": _source_anchor_world(obj),
                "circuit": _source_circuit_id(obj, prefer_group=bool(cfg.get("prefer_group_circuit", True))),
                "subgroups": hierarchy_ctx.get("subgroups", []),
                "tree_order": hierarchy_ctx.get("order_key", tuple()),
            }
        )

    if not candidates:
        if selection_mode:
            _warn(
                "No se encontraron dispositivos pendientes en la seleccion actual. "
                "Si desea procesar todo el documento, quite la seleccion y ejecute de nuevo."
            )
        _warn(
            "Resumen escaneo: "
            f"revisados={stats['scanned']}, biblioteca={stats['library']}, "
            f"estricto={stats['strict']}, conexiones2d={stats['conn2d']}, "
            f"no_tipo={stats['not_type']}, ya_con_caja={stats['existing']}, "
            f"excluidos_politica={stats['policy']}."
        )
        return

    ordered = _sort_candidates(
        candidates,
        group_by_circuit=bool(cfg.get("group_by_circuit", True)),
        preserve_hierarchy=bool(cfg.get("preserve_source_hierarchy", True)),
    )
    created = 0
    skipped = 0
    errors = 0

    try:
        doc.openTransaction("ElectricCR: colocar cajas octogonales")
        for item in ordered:
            src = item["obj"]
            src_type = item["type"]
            src_key = item["key"]
            src_circuit = item.get("circuit", "Sin_Circuito")
            src_subgroups = list(item.get("subgroups", []) or [])

            if src_key in existing_keys:
                skipped += 1
                continue

            base_type_group = g_toma if src_type == "Toma" else g_apa
            target_group = None
            if cfg.get("place_in_source_circuit_group", True):
                target_group = _ensure_source_circuit_boxes_group(doc, src, src_type)
            if target_group is None and cfg.get("preserve_source_hierarchy", True) and src_subgroups:
                target_group = _ensure_hierarchy_target_group(doc, base_type_group, src_subgroups)
            elif target_group is None and cfg.get("group_by_circuit", True):
                target_group = _ensure_circuit_type_group(doc, g_circuitos, src_circuit, src_type)
            elif target_group is None:
                target_group = base_type_group
            placement = _build_box_placement(
                src,
                anchor_local=anchor_local,
                z_offset=float(cfg.get("z_offset", DEFAULT_Z_OFFSET)),
                snpt_level=float(cfg.get("snpt", CEILING_SNPT_MM)),
            )

            try:
                label_base = _safe_text(getattr(src, "Label", "")) or _safe_text(getattr(src, "Name", ""))
                box = insert_box_link(
                    doc=doc,
                    name_prefix=f"{NAME_PREFIX} - {label_base}",
                    placement=placement,
                    diametro_emt=float(cfg.get("diameter", DEFAULT_DIAMETER)),
                    recompute=False,
                    hide_master=True,
                )
                _ensure_box_metadata(
                    box,
                    src,
                    src_type,
                    snpt_level=float(cfg.get("snpt", CEILING_SNPT_MM)),
                    circuit_id=src_circuit,
                )
                _remove_from_group(g_cajas, box)
                _add_to_group(target_group, box)
                existing_keys.add(src_key)
                created += 1
            except Exception as ex:
                errors += 1
                _warn(f"No se pudo colocar caja para '{_safe_text(getattr(src, 'Label', src.Name))}': {ex}")

        doc.recompute()
        doc.commitTransaction()
    except Exception as ex:
        try:
            doc.abortTransaction()
        except Exception:
            pass
        _err(f"Fallo general: {ex}")
        return

    destino_txt = (
        "Destino principal=<Circuito>/Cajas en origen."
        if cfg.get("place_in_source_circuit_group", True)
        else "Destino principal=electrico/Cajas/Cajas_Octogonales."
    )

    _log(
        f"Finalizado. Creadas={created}, Omitidas={skipped}, Errores={errors}. "
        f"{destino_txt} "
        f"Nivel SNPT={float(cfg.get('snpt', CEILING_SNPT_MM)):.1f} mm. "
        f"Cajas en circuito origen={'SI' if cfg.get('place_in_source_circuit_group', True) else 'NO'}. "
        f"Jerarquia origen={'SI' if cfg.get('preserve_source_hierarchy', True) else 'NO'}. "
        f"Orden por circuito={'SI' if cfg.get('group_by_circuit', True) else 'NO'}. "
        f"Escaneo(revisados={stats['scanned']}, conexiones2d={stats['conn2d']}, "
        f"ya_con_caja={stats['existing']}, excluidos={stats['policy']})."
    )


if __name__ == "__main__":
    main()

# -*- coding: utf-8 -*-
# MenuText: Analizar áreas rectangulares desde muros BIM
# ToolTip: Seleccione uno o varios muros BIM y cree el análisis rectangular de áreas.
# Toolbar: Areas
# Transaction: self

from __future__ import annotations

import os

macro_dir = os.path.dirname(os.path.abspath(__file__))
launcher = os.path.abspath(os.path.join(macro_dir, os.pardir, os.pardir, "AnalizarAreasDesdeMuroBIM.FCMacro"))
if not os.path.isfile(launcher):
    raise RuntimeError("No se encontró AnalizarAreasDesdeMuroBIM.FCMacro")

namespace = {"__name__": "__main__", "__file__": launcher}
exec(compile(open(launcher, "rb").read(), launcher, "exec"), namespace)
